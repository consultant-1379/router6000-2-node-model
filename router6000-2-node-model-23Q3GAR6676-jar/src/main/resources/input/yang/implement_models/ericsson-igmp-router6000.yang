module ericsson-igmp-router6000 {
  yang-version "1";

  namespace "urn:rdns:com:ericsson:oammodel:ericsson-igmp-router6000";

  prefix "igmpr6k";

  import ericsson-types-router6000 {
    prefix "typesrouter6000";
  }

  import ericsson-contexts-router6000 {
    prefix "ctxsr6k";
  }

  import ietf-inet-types {
    prefix "inet";
  }

  import ericsson-context-router6000 {
    prefix "ctxr6k";
  }

  import ericsson-yang-extensions {
    prefix "yexte";
  }

  organization
    "Ericsson AB";

  contact
    "Web:   <http://www.ericsson.com>";

  description
    "ericsson-igmp-router6000
     Copyright (c) 2022 Ericsson AB.
     All rights reserved";

  revision "2022-11-04" {
    description
      "Remove all bulkstats configuration";
    reference
      "rfc6020";
    yexte:version "2";
    yexte:release "0";
    yexte:correction "1";
  }

  revision "2018-06-05" {
    description
      "Change model namespace";
    reference
      "rfc6020";
    yexte:version "2";
    yexte:release "0";
    yexte:correction "0";
  }

  revision "2016-12-20" {
    description
      "add default value";
    reference
      "rfc6020";
    yexte:version "1";
    yexte:release "0";
    yexte:correction "0";
  }

  revision "2016-04-27" {
    description
      "initial revision";
    reference
      "rfc6020";
  }

  grouping igmp-service-profile-grp {
    description
      "IGMP service profile mode";
    /*
    priority (priority-val)
    */
    leaf priority {
      type uint8 {
        range "0..10";
      }
      default "0";
      description
        "specify IGMP service priority";
    }
    /*
    max-groups (group-val) [ drop-old ]
    */
    container max-groups {
      presence "";
      description
        "specify maximum number of groups per circuit";
      leaf group-val {
        type uint32 {
          range "1..100000";
        }
        mandatory true;
        description
          "maximum number of joiners";
      }
      leaf drop-old {
        type empty;
        description
          "drop old group if max-groups is exceeded";
      }
    }
    /*
    instant-leave
    */
    leaf instant-leave {
      type empty;
      description
        "turn on instant leave on this interface";
    }
    /*
    bulkstats
    */
    leaf bulkstats {
      type empty;
      status obsolete;
      description
        "Generate IGMP statistics for bulkstats";
    }
    /*
    sticky-groups (acl-name)
    */
    leaf sticky-groups {
      type string;
      description
        "specify list of sticky groups";
    }
    /*
    access-group (acl-name)
    */
    leaf access-group {
      type string;
      description
        "specify IGMP access group list";
    }
    /*
    static-group (grp-addr)
    */
    list static-group {
      key "static-group";
      description
        "specify list of static groups";
      leaf static-group {
        type typesrouter6000:ipv4-muticast-address;
        description
          "Multicast group IP address, should be in the range
           224.0.1.0 to 239.255.255.255";
      }
    }
    /*
    multicast { < destination (dest-intf) (dest-cxt) [ group-
     list (acl-name) ] > | < adjust-qos-rate { queuing [ minimum-
     rate (rate-val) ] | delay-interval (intvl-val) } > }
    */
    container multicast {
      description
        "Configure multicast specific commands";
      container destination {
        description
          "Configure multicast destination";
        leaf dest-intf {
          type string;
          mandatory true;
          description
            "Multicast destination interface name";
        }
        leaf dest-cxt {
          type string;
          mandatory true;
          description
            "Multicast destination context name";
        }
        leaf group-list {
          type string;
          description
            "Specify group list for multicast destination";
        }
      }
      container adjust-qos-rate {
        description
          "Adjust qos binding rate";
        container queuing {
          presence "";
          description
            "Apply adjusted qos rate on queuing binding";
          leaf minimum-rate {
            type uint32 {
              range "64..4294967295";
            }
            default "64";
            description
              "Minimum rate to avoid starving unicast traffic";
          }
        }
        leaf delay-interval {
          type uint8 {
            range "1..10";
          }
          default "5";
          description
            "Time interval after which rate adjustment applies";
        }
      }
    }
    /*
    ssm-map (map-source) (acl-name)
    */
    list ssm-map {
      key "map-source acl-name";
      description
        "Configure SSM mapping";
      leaf map-source {
        type inet:ipv4-address;
        description
          "Multicast  source IP address";
      }
      leaf acl-name {
        type string;
        description
          "Group access list name";
      }
    }
    /*
    static-group-src (grp-addr) (src-addr)
    */
    list static-group-src {
      key "grp-addr src-addr";
      description
        "specify list of static groups";
      leaf grp-addr {
        type typesrouter6000:ipv4-muticast-address;
        description
          "Multicast group IP address, should be in the range
           224.0.1.0 to 239.255.255.255";
      }
      leaf src-addr {
        type inet:ipv4-address;
        description
          "Multicast source IP address";
      }
    }
  }

  augment "/ctxsr6k:contexts/ctxr6k:context" {
    description
      "ericsson-igmp";
    /*
    igmp { mtrace-prohibit | < group-bandwidth (rate-val)
     {group-list (list-name)} [ qos-adjust [ average-packet-size
     (size-val) ] [ no-oif ] ] > | service-profile (profile-tag)
     }
    */
    container igmp {
      description
        "IGMP global configuration command";
      leaf mtrace-prohibit {
        type empty;
        description
          "Administratively prohibit mtrace";
      }
      list group-bandwidth {
        key "group-list";
        description
          "Configure group bandwidth recommendation";
        leaf group-list {
          type string;
          description
            "Specify access-list for IGMP groups";
        }
        leaf rate-val {
          type uint16 {
            range "1..65535";
          }
          mandatory true;
          description
            "1-65535 kbps";
        }
        container qos-adjust {
          presence "";
          description
            "Adjust qos rate for this multicast-group";
          leaf average-packet-size {
            type uint16 {
              range "64..9000";
            }
            description
              "Average multicast packet size in bytes";
          }
          leaf no-oif {
            type empty;
            description
              "Do not create OIF for this multicast group";
          }
        }
      }
      list service-profile {
        key "service-profile";
        description
          "Configure service profile for igmp";
        leaf service-profile {
          type string;
          description
            "Name of service-profile";
        }
        uses igmp-service-profile-grp;
      }
    }
  }

}
