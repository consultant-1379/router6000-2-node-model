/*
    This is written manually.
*/

module ericsson-synchronization-dev-router6676 {
  yang-version "1";

  namespace "urn:rdns:com:ericsson:oammodel:ericsson-synchronization-dev-router6676";

  prefix "syncvrouter6676";

  import ericsson-synchronization-router6000 {
    prefix "syncr6000";
  }

  import ericsson-contexts-router6000 {
   prefix "ctxsr6k";
  }

  import ericsson-yang-extensions {
    prefix "yexte";
  }

  organization
    "Ericsson AB";

  contact
    "Web:   <http://www.ericsson.com>";

  description
    "ericsson-synchronization-dev-router6676
     Copyright (c) 2022 Ericsson AB.
     All rights reserved";

  revision "2022-11-03" {
    description
      "unsupported for high-impedance-standby and cable-delay value2";
    reference
      "rfc6020";
    yexte:version "1";
    yexte:release "3";
    yexte:correction "0";
  }

  revision "2022-07-06" {
    description
      "supported for gnss-dampening and hold-off";
    reference
      "rfc6020";
    yexte:version "1";
    yexte:release "2";
    yexte:correction "0";
  }

  revision "2022-05-26" {
    description
      "remove deviation for gnss-dampening and hold-off";
    reference
      "rfc6020";
    yexte:version "1";
    yexte:release "1";
    yexte:correction "1";
  }

  revision "2021-11-08" {
    description
      "unsupported for gnss-dampening and hold-off";
    reference
      "rfc6020";
    yexte:version "1";
    yexte:release "1";
    yexte:correction "0";
  }

  revision "2021-10-18" {
    description
      "Add deviation for gnss-dampening and hold-off";
    reference
      "rfc6020";
    yexte:version "1";
    yexte:release "0";
    yexte:correction "1";
  }

  revision "2020-04-07" {
    description
      "deviation for ericsson-synchronization-router6000 file.";
    reference
      "rfc6020";
    yexte:version "1";
    yexte:release "0";
    yexte:correction "0";
  }

  deviation "/ctxsr6k:contexts/syncr6000:synchronization/syncr6000:tod/syncr6000:tod-choice/syncr6000:input/syncr6000:input/syncr6000:high-impedance-standby" {
    deviate not-supported;
  }
  deviation "/ctxsr6k:contexts/syncr6000:synchronization/syncr6000:tod/syncr6000:tod-choice/syncr6000:input/syncr6000:input/syncr6000:cable-delay/syncr6000:value2" {
    deviate not-supported;
  }
  deviation "/ctxsr6k:contexts/syncr6000:synchronization/syncr6000:ptp-clock/syncr6000:ptp-clock/syncr6000:g8275-1-t-bc/syncr6000:g8275-1-t-bc/syncr6000:g8275-1-t-bc/syncr6000:ptp-port/syncr6000:port-id" {
    deviate replace {
      type uint16 {
        range "1..128";
      }
    }
  }
  deviation "/ctxsr6k:contexts/syncr6000:synchronization/syncr6000:ptp-clock/syncr6000:ptp-clock/syncr6000:g8275-1-t-bc/syncr6000:g8275-1-t-bc/syncr6000:g8275-2-t-bc-p/syncr6000:ptp-port/syncr6000:port-id" {
    deviate replace {
      type uint16 {
        range "1..128";
      }
    }
  }
  deviation "/ctxsr6k:contexts/syncr6000:synchronization/syncr6000:ptp-clock/syncr6000:ptp-clock/syncr6000:v1588v2-boundary/syncr6000:v1588v2-boundary/syncr6000:ptp-port/syncr6000:ptp-port" {
    deviate replace {
      type uint16 {
        range "1..128";
      }
    }
  }
}
