module ericsson-rsvp-router6000 {
  yang-version "1";

  namespace "urn:rdns:com:ericsson:oammodel:ericsson-rsvp-router6000";

  prefix "rsvpr6k";

  import ietf-inet-types {
    prefix "inet";
  }

  import ietf-interfaces {
    prefix "if";
  }

  import ericsson-contexts-router6000 {
    prefix "ctxsr6k";
  }

  import ericsson-types-router6000 {
    prefix "typesrouter6000";
  }

  import ericsson-key-chain-router6000 {
    prefix "keychainrouter6000";
  }

  import ericsson-te-router6000 {
    prefix "terouter6000";
  }

  import ericsson-context-router6000 {
    prefix "ctxr6k";
  }

  import ericsson-yang-extensions {
    prefix "yexte";
  }

  organization
    "Ericsson AB";

  contact
    "Web:   <http://www.ericsson.com>";

  description
    "ericsson-rsvp-router6000
     Copyright (c) 2023 Ericsson AB.
     All rights reserved";

  revision "2023-03-07" {
    description
      "IA23789 Fix for admin-group on ENM";
    reference
      "rfc6020";
    yexte:version "2";
    yexte:release "3";
    yexte:correction "3";
  }

  revision "2021-08-02" {
    description
      "R6K-1430 ENM SI: Fix for default values not displayed on
       ENM";
    reference
      "rfc6020";
    yexte:version "2";
    yexte:release "3";
    yexte:correction "2";
  }

  revision "2021-04-26" {
    description
      "change default value for window-size";
    reference
      "rfc6020";
    yexte:version "2";
    yexte:release "3";
    yexte:correction "1";
  }

  revision "2021-02-08" {
    description
      "add support for authentication key";
    reference
      "rfc6020";
    yexte:version "2";
    yexte:release "3";
    yexte:correction "0";
  }

  revision "2020-11-27" {
    description
      "add support for setup-delay, secondary lsp and hold-time
       commands";
    reference
      "rfc6020";
    yexte:version "2";
    yexte:release "2";
    yexte:correction "0";
  }

  revision "2020-07-28" {
    description
      "add admin-distance config support";
    reference
      "rfc6020";
    yexte:version "2";
    yexte:release "1";
    yexte:correction "0";
  }

  revision "2018-11-27" {
    description
      "remove ipos choice description";
    reference
      "rfc6020";
    yexte:version "2";
    yexte:release "0";
    yexte:correction "1";
  }

  revision "2018-06-05" {
    description
      "Change model namespace";
    reference
      "rfc6020";
    yexte:version "2";
    yexte:release "0";
    yexte:correction "0";
  }

  revision "2018-04-20" {
    description
      "Change in re-optimation min interval from 60 to 5";
    reference
      "rfc6020";
    yexte:version "1";
    yexte:release "0";
    yexte:correction "3";
  }

  revision "2017-11-15" {
    description
      "JIRA:IPOS-16499 in command'rsvp explict-route xx nexthop
       ipaddr' ipaddr must odered-by user";
    reference
      "rfc6020";
    yexte:version "1";
    yexte:release "0";
    yexte:correction "2";
  }

  revision "2017-08-10" {
    description
      "JIRA:IPOS-14430 delete must condition";
    reference
      "rfc6020";
    yexte:version "1";
    yexte:release "0";
    yexte:correction "1";
  }

  revision "2017-01-03" {
    description
      "modify all failed cases";
    reference
      "rfc6020";
    yexte:version "1";
    yexte:release "0";
    yexte:correction "0";
  }

  revision "2016-05-31" {
    description
      "change the type of bandwidth";
    reference
      "rfc6020";
  }

  revision "2016-03-29" {
    description
      "For CLI2Yang models data node sequence change.";
    reference
      "rfc6020";
  }

  revision "2015-12-07" {
    description
      "initial revision";
    reference
      "rfc6020";
  }

  grouping rsvp-grp {
    description
      "RSVP configuration mode";
    /*
    interface (intf-name)
    */
    list interface {
      key "interface";
      description
        "Configure RSVP interface";
      leaf interface {
        type leafref {
          path "/if:interfaces/if:interface/if:name";
        }
        description
          "Interface name";
      }
      uses rsvp-if-grp;
    }
    /*
    link-attributes
    */
    container link-attributes {
      must "./attribute/attr-name and ./attribute/attr-value" {
        error-message "Must configure an attribute or delete "
        + "link attributes";
        description
          "Must configure an attribute or delete link
           attributes";
      }
      presence "";
      description
        "Configure RSVP-TE link attributes";
      uses rsvp-link-attr-grp;
    }
    /*
    log-lsp-up-down
    */
    leaf log-lsp-up-down {
      type empty;
      description
        "Log RSVP lsp state transitions";
    }
    /*
    log-nbr-up-down
    */
    leaf log-nbr-up-down {
      type empty;
      description
        "Log RSVP neighbor up or down events";
    }
    /*
    log-errors
    */
    leaf log-errors {
      type empty;
      description
        "Log RSVP error events";
    }
    /*
    frr-auto-revert-delay (delay-value)
    */
    leaf frr-auto-revert-delay {
      type uint16 {
        range "0..65535";
      }
      description
        "Configure delay before switching back from a FRR path
         (in secs)";
    }
    /*
    explicit-null
    */
    leaf explicit-null {
      type empty;
      description
        "Enable explicit-null label";
    }
    /*
    explicit-route (route-string)
    */
    list explicit-route {
      key "explicit-route";
      description
        "Configure explicit route";
      leaf explicit-route {
        type string;
        description
          "Explicit-route name";
      }
      uses rsvp-explicit-route-grp;
    }
    /*
    lsp (lsp-string) [ backup-for (prim-string) | bypass
     (bypass-addr) [ node-protect-lsp-egress (node-egress) ] |
     secondary-for (sec-prim-string) ]
    */
    list lsp {
      key "lsp-string";
      description
        "Configure Label Switched Path";
      leaf lsp-string {
        type string;
        description
          "LSP name";
      }
      choice lsp-opt {
        case backup-for {
          leaf backup-for {
            type leafref {
              path "/ctxsr6k:contexts/ctxr6k:context/ctxr6k:router"
              + "/rsvpr6k:rsvp/rsvpr6k:lsp/rsvpr6k:lsp-string";
            }
            description
              "Configure a backup Label Switched Path";
          }
        }
        case bypass {
          container bypass {
            must "../local-protection" {
              error-message "please configuration local- "
              + "protection";
              description
                "Must configuration local-protection";
            }
            presence "";
            description
              "Fast ReRoute bypass LSP";
            leaf bypass-addr {
              type inet:ipv4-address;
              mandatory true;
              description
                "Fast ReRoute bypass IP address";
            }
            leaf node-protect-lsp-egress {
              type inet:ipv4-address;
              description
                "Fast ReRoute node-protection egress address";
            }
          }
        }
        case secondary-for {
          leaf secondary-for {
            type leafref {
              path "/ctxsr6k:contexts/ctxr6k:context/ctxr6k:router"
              + "/rsvpr6k:rsvp/rsvpr6k:lsp/rsvpr6k:lsp-string";
            }
            description
              "Configure a secondary Label Switched Path";
          }
        }
      }
      uses rsvp-lsp-grp;
    }
    /*
    igp-shortcut
    */
    leaf igp-shortcut {
      type empty;
      description
        "Enable IGP shortcut for all RSVP LSPs";
    }
    /*
    tunnel-shortcut
    */
    leaf tunnel-shortcut {
      type empty;
      description
        "Enable tunnel shortcut for all RSVP LSPs";
    }
    /*
    rro-prefix-type { router-id | interface }
    */
    leaf rro-prefix-type {
      type enumeration {
        enum router-id {
          value 0;
          description
            "RRO IP Prefix Using Router ID";
        }
        enum interface {
          value 1;
          description
            "RRO IP Prefix Using Outbound Interface Address";
        }
      }
      default "router-id";
      description
        "RSVP RRO IP Prefix Type";
    }
    /*
    retry-timer (timer-value)
    */
    leaf retry-timer {
      type uint32 {
        range "1..4294967295";
      }
      default "30";
      description
        "RSVP-TE retry timer";
    }
    /*
    retry-limit (limit-value)
    */
    leaf retry-limit {
      type uint32 {
        range "1..4294967295";
      }
      default "4294967295";
      description
        "RSVP-TE retry limit";
    }
    /*
    over-subscription-factor (factor-value)
    */
    leaf over-subscription-factor {
      type uint32 {
        range "1..4294967295";
      }
      description
        "Reservable subscription factor";
    }
    /*
    constraint (constraint-name)
    */
    list constraint {
      key "constraint";
      description
        "Configure RSVP-TE constraint";
      leaf constraint {
        type string;
        description
          "Constraint name";
      }
      uses rsvp-constr-grp;
    }
    /*
    track (name-string)
    */
    list track {
      key "track";
      description
        "Configure a RSVP track object";
      leaf track {
        type string;
        description
          "Track object name";
      }
      uses rsvp-track-obj-grp;
    }
    /*
    graceful-restart [ restart-time (restart-val) | recovery-
     time (recovery-val) | helper | maximum_helper_restart-time
     (restart-val) | maximum_helper_recovery-time (recovery-val)
     ]
    */
    container graceful-restart {
      presence "";
      description
        "Enable RSVP graceful restart";
      leaf restart-time {
        type uint16 {
          range "10..1800";
        }
        default "30";
        description
          "Configure Graceful Restart restart time";
      }
      leaf recovery-time {
        type uint16 {
          range "20..3600";
        }
        default "60";
        description
          "Configure Graceful Restart recovery time";
      }
      leaf helper {
        type boolean;
        default "true";
        description
          "Enable/Disable helper";
      }
      leaf maximum_helper_restart-time {
        type uint16 {
          range "10..1800";
        }
        description
          "Configure RSVP GR maximum helper restart time";
      }
      leaf maximum_helper_recovery-time {
        type uint16 {
          range "20..3600";
        }
        description
          "Configure RSVP GR maximum helper recovery time";
      }
    }
    /*
    te-update { delay (interval-val) | threshold (thres-val) }
    */
    container te-update {
      description
        "Configure TE IGP advertisement parameters";
      leaf delay {
        type uint16 {
          range "0..3600";
        }
        description
          "Configure TE IGP advertisement delay";
      }
      leaf threshold {
        type uint8 {
          range "0..100";
        }
        description
          "Configure TE bandwidth reservation threshold required
           for IGP advertisement";
      }
    }
    /*
    bfd
    */
    leaf bfd {
      type empty;
      description
        "Enable Bidirectional Forwarding Detection";
    }
    /*
    auto-frr
    */
    leaf auto-frr {
      type empty;
      description
        "Enables auto frr";
    }
    /*
    reoptimization [ interval (interval-val) ]
    */
    container reoptimization {
      presence "";
      description
        "Enables periodic Reoptimization";
      leaf interval {
        type uint32 {
          range "5..527040";
        }
        default "1440";
        description
          "Configures Reoptimization time";
      }
    }
    /*
    setup-delay [ secondary (interval-val) ]
    */
    container setup-delay {
      presence "";
      description
        "Configure setup delay for LSP";
      leaf secondary {
        type uint8 {
          range "0..60";
        }
        default "5";
        description
          "Configure secondary lsp setup delay (in seconds)";
      }
    }
    /*
    hold-time (hold-time-val)
    */
    leaf hold-time {
      type uint8 {
        range "0..60";
      }
      default "10";
      description
        "Configure Hold Time (in seconds)";
    }
    /*
    distance (distance-id)
    */
    leaf distance {
      type uint8 {
        range "1..255";
      }
      default "6";
      description
        "Assign admin distance value";
    }
  }

  grouping rsvp-constr-grp {
    description
      "RSVP-TE Constraint Mode";
    /*
    admin-group { exclude | include-any | include-all }
     (attributes) (attributes_new)
    */
    container admin-group {
      description
        "Configure administrative group";
      container exclude {
        description
          "Configure excluded admin groups";
        leaf-list attributes {
          type leafref {
            path "/ctxsr6k:contexts/ctxr6k:context/ctxr6k:router"
            + "/rsvpr6k:rsvp/rsvpr6k:link-attributes/rsvpr6k:attribute"
            + "/rsvpr6k:attr-name";
          }
          status obsolete;
          description
            "leaf-list attributes.";
        }
        leaf-list attributes_new {
          type string;
          description
            "leaf-list attributes_new.";
        }
      }
      container include-any {
        description
          "Configure include-any admin groups";
        leaf-list attributes {
          type leafref {
            path "/ctxsr6k:contexts/ctxr6k:context/ctxr6k:router"
            + "/rsvpr6k:rsvp/rsvpr6k:link-attributes/rsvpr6k:attribute"
            + "/rsvpr6k:attr-name";
          }
          status obsolete;
          description
            "leaf-list attributes.";
        }
        leaf-list attributes_new {
          type string;
          description
            "leaf-list attributes_new.";
        }
      }
      container include-all {
        description
          "Configure include-all admin groups";
        leaf-list attributes {
          type leafref {
            path "/ctxsr6k:contexts/ctxr6k:context/ctxr6k:router"
            + "/rsvpr6k:rsvp/rsvpr6k:link-attributes/rsvpr6k:attribute"
            + "/rsvpr6k:attr-name";
          }
          status obsolete;
          description
            "leaf-list attributes.";
        }
        leaf-list attributes_new {
          type string;
          description
            "leaf-list attributes_new.";
        }
      }
    }
    /*
    exclude { node (node-value) | link (link-value) }
    */
    container exclude {
      description
        "Configure nodes to exclude";
      list node {
        key "node";
        description
          "Node type";
        leaf node {
          type inet:ipv4-address;
          description
            "IP address of the node to exclude";
        }
      }
      list link {
        key "link";
        description
          "Link type";
        leaf link {
          type inet:ipv4-address;
          description
            "IP address of the link to exclude";
        }
      }
    }
    /*
    minimum-bandwidth (bandwidth-value) [bandwidth-value-type]
    */
    container minimum-bandwidth {
      presence "";
      description
        "Configure minimum bandwidth required";
      leaf bandwidth-value {
        type uint32 {
          range "1..4294967295";
        }
        mandatory true;
        description
          "Reservable bandwidth";
      }
      leaf bandwidth-value-type {
        type typesrouter6000:bandwidth_value_type;
        description
          "Bandwidth value type";
      }
    }
    /*
    priority (priority-setup) [ (priority-hold) ]
    */
    container priority {
      presence "";
      description
        "Configure LSP priority";
      leaf priority-setup {
        type uint8 {
          range "0..7";
        }
        mandatory true;
        description
          "Setup priority";
      }
      leaf priority-hold {
        type uint8 {
          range "0..7";
        }
        default "0";
        description
          "Hold priority";
      }
    }
    /*
    hop-limit (limit-value)
    */
    leaf hop-limit {
      type uint8 {
        range "2..255";
      }
      description
        "Configure hop limit";
    }
  }

  grouping rsvp-if-grp {
    description
      "RSVP interface configuration mode";
    /*
    refresh-interval (interval-val)
    */
    leaf refresh-interval {
      type uint16 {
        range "5..65535";
      }
      description
        "Configure interface refresh interval";
    }
    /*
    te-metric (metric-val)
    */
    leaf te-metric {
      type uint8 {
        range "1..128";
      }
      description
        "Configure interface TE metric";
    }
    /*
    keep-multiplier (multiplier-val)
    */
    leaf keep-multiplier {
      type uint8 {
        range "1..255";
      }
      default "3";
      description
        "Configure interface keep multiplier";
    }
    /*
    hello { interval (interval-val) | keep-multiplier
     (multiplier-val) }
    */
    container hello {
      description
        "Configure interface hello parameters";
      leaf interval {
        type uint8 {
          range "1..60";
        }
        description
          "Configure interface hello interval";
      }
      leaf keep-multiplier {
        type uint8 {
          range "1..255";
        }
        default "3";
        description
          "Configure interface hello keep multiplier";
      }
    }
    /*
    bandwidth (bandwidth-value) [bandwidth-value-type]
    */
    container bandwidth {
      presence "";
      description
        "Configure interface bandwidth";
      leaf bandwidth-value {
        type uint32 {
          range "1..4294967295";
        }
        mandatory true;
        description
          "Reservable bandwidth";
      }
      leaf bandwidth-value-type {
        type typesrouter6000:bandwidth_value_type;
        description
          "Bandwidth value type";
      }
    }
    /*
    admin-group < group-value (group-value-fake) > (group-value-
     fake-new)
    */
    container admin-group {
      description
        "Associate the interface with admin groups";
      leaf-list group-value {
        type leafref {
          path "/ctxsr6k:contexts/ctxr6k:context/ctxr6k:router"
          + "/rsvpr6k:rsvp/rsvpr6k:link-attributes/rsvpr6k:attribute"
          + "/rsvpr6k:attr-name";
        }
        status obsolete;
        description
          "Associate the interface with admin groups";
      }
      leaf-list group-value-fake-new {
        type string;
        description
          "leaf-list group-value-fake-new.";
      }
    }
    /*
    graceful-restart { restart-time (restart-val) | recovery-
     time (recovery-val) }
    */
    container graceful-restart {
      description
        "Enable Graceful Restart";
      leaf restart-time {
        type uint16 {
          range "10..1800";
        }
        default "30";
        description
          "Configure Graceful Restart restart time";
      }
      leaf recovery-time {
        type uint16 {
          range "20..3600";
        }
        default "60";
        description
          "Configure Graceful Restart recovery time";
      }
    }
    /*
    bfd
    */
    leaf bfd {
      type empty;
      description
        "Enable Bidirectional Forwarding Detection";
    }
    /*
    authentication (key-chain)
    */
    leaf authentication {
      type string;
      status obsolete;
      description
        "Configure MD5 authentication for interface";
    }
    /*
    authentication-config (key-chain) [window-size (win-val)]
     [hmac-cryptographic {enable | disable}] [sa-life-time (time-
     val)]
    */
    container authentication-config {
      presence "";
      description
        "Configure MD5 authentication for interface";
      leaf key-chain {
        type leafref {
          path "/ctxsr6k:contexts/ctxr6k:context"
          + "/keychainrouter6000:key-chain/keychainrouter6000:key-chain";
        }
        mandatory true;
        description
          "key-chain identifier";
      }
      leaf window-size {
        type uint8 {
          range "1..64";
        }
        default "16";
        description
          "Specify maximum number of rsvp packets can be
           received out of order";
      }
      leaf hmac-cryptographic {
        type enumeration {
          enum enable {
            value 0;
            description
              "Enable hmac-cryptographic type";
          }
          enum disable {
            value 1;
            description
              "Disable hmac-cryptographic type(default)";
          }
        }
        default "disable";
        description
          "Configure hmac-cryptographic authentication type";
      }
      leaf sa-life-time {
        type uint32 {
          range "300..86400";
        }
        default "1800";
        description
          "configure life-time(in seconds) for each security
           association";
      }
    }
  }

  grouping rsvp-link-attr-grp {
    description
      "RSVP link attribute mode";
    /*
    attribute (attr-name) (attr-value)
    */
    list attribute {
      key "attr-name";
      description
        "Configure administrative group";
      leaf attr-name {
        type string;
        description
          "Attribute name";
      }
      leaf attr-value {
        type uint8 {
          range "0..31";
        }
        mandatory true;
        description
          "Attribute value";
      }
    }
  }

  grouping rsvp-explicit-route-grp {
    description
      "RSVP explicit route configuration mode";
    /*
    next-hop (next-hop) [ loose | strict ]
    */
    list next-hop {
      key "next-hop";
      ordered-by user;
      description
        "Next hop on the explicit path";
      leaf next-hop {
        type inet:ipv4-address;
        description
          "Next-hop IP address";
      }
      leaf next-hop-opt {
        type enumeration {
          enum loose {
            value 0;
            description
              "Next-hop may be more than one hop away";
          }
          enum strict {
            value 1;
            description
              "(default) Next-hop must be one hop away";
          }
        }
        description
          "leaf next-hop-opt.";
      }
    }
  }

  grouping rsvp-lsp-grp {
    description
      "RSVP LSP configuration mode";
    /*
    record-route
    */
    leaf record-route {
      type boolean;
      default "true";
      description
        "Enable/Disable record-route";
    }
    /*
    ingress (ingress-addr)
    */
    leaf ingress {
      type inet:ipv4-address;
      description
        "LSP ingress node";
    }
    /*
    egress (egress-addr)
    */
    leaf egress {
      when "not (../bypass/node-protect-lsp-egress)" {
        description
          "";
      }
      type inet:ipv4-address;
      description
        "LSP egress node";
    }
    /*
    fast-reroute nnhop-intf-address (nnhop-addr)
    */
    container fast-reroute {
      when "../bypass/node-protect-lsp-egress" {
        description
          "";
      }
      description
        "Fast Reroute for node-protection";
      leaf nnhop-intf-address {
        type inet:ipv4-address;
        description
          "Next Next-hop Interface Address for Node Protection";
      }
    }
    /*
    shutdown
    */
    leaf shutdown {
      type empty;
      description
        "Shutdown the LSP";
    }
    /*
    source-path (path-name)
    */
    leaf source-path {
      type leafref {
        path "/ctxsr6k:contexts/ctxr6k:context/ctxr6k:router"
        + "/rsvpr6k:rsvp/rsvpr6k:explicit-route/rsvpr6k:explicit-route";
      }
      must "not (../dynamic-path) and not (../constraint) and not(.."
      + "/cspf)" {
        error-message "please remove dynamic-path settings "
        + "first";
        description
          "source-path can be configured once without
           dynamic-path configuration";
      }
      description
        "Specify an explicit source path to use";
    }
    /*
    dynamic-path (path-name)
    */
    leaf dynamic-path {
      type leafref {
        path "/ctxsr6k:contexts/ctxr6k:context/ctxr6k:router"
        + "/rsvpr6k:rsvp/rsvpr6k:explicit-route/rsvpr6k:explicit-route";
      }
      must "not(../source-path)" {
        error-message "please remove source-path settings first";
        description
          "dynamic-path can be configured once without
           source-path configuration";
      }
      description
        "Specify an dynamic (CSPF) path to use";
    }
    /*
    description (description-str)
    */
    leaf description {
      type string;
      description
        "Set description string";
    }
    /*
    igp-shortcut
    */
    leaf igp-shortcut {
      type empty;
      description
        "Enable IGP shortcut";
    }
    /*
    tunnel-shortcut
    */
    leaf tunnel-shortcut {
      when "not (../bypass) and not (../backup-for) and not (.."
      + "/secondary-for)" {
        description
          "";
      }
      type empty;
      must "not (../rsvpr6k:exclusive)" {
        error-message "please don't configure tunnel-shortcut "
        + "when exclusive is set";
        description
          "tunnel-shortcut can be configured in lsp";
      }
      description
        "Enable tunnel shortcut";
    }
    /*
    local-protection
    */
    leaf local-protection {
      type boolean;
      default "true";
      description
        "Enable/Disable local-protection";
    }
    /*
    constraint (constraint-name)
    */
    leaf constraint {
      type leafref {
        path "/ctxsr6k:contexts/ctxr6k:context/ctxr6k:router"
        + "/rsvpr6k:rsvp/rsvpr6k:constraint/rsvpr6k:constraint";
      }
      must "not(../source-path)" {
        error-message "please remove source-path settings first";
        description
          "constraint can be configured once without source-path
           configuration";
      }
      description
        "Set LSP constraint";
    }
    /*
    cspf
    */
    leaf cspf {
      type empty;
      must "not(../source-path)" {
        error-message "please remove source-path settings first";
        description
          "cspf can be configured once without source-path
           configuration";
      }
      description
        "enable CSPF path calculations";
    }
    /*
    track (track-name)
    */
    leaf track {
      type string;
      description
        "Specify the object LSP needs to track";
    }
    /*
    exclusive
    */
    leaf exclusive {
      when "not (../bypass) and not (../backup-for) and not (.."
      + "/secondary-for)" {
        description
          "";
      }
      type empty;
      description
        "LSP is exclusive to mapped VLLs only";
    }
  }

  grouping rsvp-track-obj-grp {
    description
      "RSVP track object configuration mode";
    /*
    interface (intf-name)
    */
    list interface {
      key "interface";
      description
        "RSVP interface to track";
      leaf interface {
        type leafref {
          path "/ctxsr6k:contexts/ctxr6k:context/ctxr6k:router"
          + "/rsvpr6k:rsvp/rsvpr6k:interface/rsvpr6k:interface";
        }
        description
          "RSVP Interface name";
      }
    }
  }

  augment "/ctxsr6k:contexts/ctxr6k:context/ctxr6k:router" {
    description
      "ericsson-rsvp";
    /*
    rsvp
    */
    container rsvp {
      when "../../ctxr6k:context-name='local'" {
        description
          "";
      }
      presence "";
      description
        "Resource Reservation Protocol (RSVP)";
      uses rsvp-grp;
    }
  }

}
