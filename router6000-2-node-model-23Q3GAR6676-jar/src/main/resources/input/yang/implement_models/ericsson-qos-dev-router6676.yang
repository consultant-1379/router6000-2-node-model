/*
    This is written manually.
*/

module ericsson-qos-dev-router6676 {
  yang-version "1";

  namespace "urn:rdns:com:ericsson:oammodel:ericsson-qos-dev-router6676";

  prefix "qosvirouter6676";

  import ericsson-qos-router6000 {
    prefix "qosrouter6000";
  }
  import ericsson-qos-config-router6000 {
    prefix "qoscfgr6k";
  }
  import ericsson-context-router6000 {
    prefix "ctxr6k";
  }
  import ericsson-contexts-router6000 {
    prefix "ctxsr6k";
  }
  import ericsson-yang-extensions {
    prefix "yexte";
  }

  organization
    "Ericsson AB";

  contact
    "Web:   <http://www.ericsson.com>";

  description
    "ericsson-qos-dev-router6676
     Copyright (c) 2022 Ericsson AB.
     All rights reserved";

  revision "2023-07-09" {
    description
      "update default burst of pwfq pir/cir";
    reference
      "rfc6020";
    yexte:version "1";
    yexte:release "0";
    yexte:correction "1";
  }

  revision "2022-09-22" {
    description
      "deviation file for 6676";
    reference
      "rfc6020";
    yexte:version "1";
    yexte:release "0";
    yexte:correction "0";
  }

  /*R6676:change range from "20..300000000" to "22:300000000"*/
  deviation "/qosrouter6000:qos/qosrouter6000:policy/qosrouter6000:policy-choice/qosrouter6000:policing/qosrouter6000:policing/"
  + "qosrouter6000:rate/qosrouter6000:rate-num" {
    deviate replace {
      type uint32 {
        range "22..300000000";
      }
    }
  }

  /*change range from "1000..523264" to "125..4000000"*/
  deviation "/qosrouter6000:qos/qosrouter6000:policy/qosrouter6000:policy-choice/qosrouter6000:policing/qosrouter6000:policing/"
  + "qosrouter6000:rate/qosrouter6000:rate-choice/qosrouter6000:burst/qosrouter6000:burst" {
    deviate replace {
      type uint32 {
        range "125..4000000";
      }
    }
  }

  /*R6676: change range from "20..300000000" to "22..300000000"*/
  deviation "/qosrouter6000:qos/qosrouter6000:policy/qosrouter6000:policy-choice/qosrouter6000:policing/qosrouter6000:policing/"
  + "qosrouter6000:rate/qosrouter6000:excess-rate" {
     deviate replace {
      type uint32 {
        range "22..300000000";
      }
    }
  }

  /*change range from "0..33292" to 125..4000000*/
  deviation "/qosrouter6000:qos/qosrouter6000:policy/qosrouter6000:policy-choice/qosrouter6000:policing/qosrouter6000:policing/"
  +  "qosrouter6000:rate/qosrouter6000:rate-opt1/qosrouter6000:excess-burst/qosrouter6000:excess-burst" {
    deviate replace {
      type int32 {
        range "125..4000000";
      }
    }
  }

   /*change queue min rate from "0..10000000" to "0..100000000"*/
  deviation "/qosrouter6000:qos/qosrouter6000:policy/qosrouter6000:policy-choice/qosrouter6000:pwfq/qosrouter6000:pwfq/qosrouter6000:queue/qosrouter6000:queue-choice/"
  + "qosrouter6000:rate/qosrouter6000:rate-choice/qosrouter6000:minimum-guarantee/qosrouter6000:minimum-guarantee-choice/qosrouter6000:rate-num/qosrouter6000:rate-num/qosrouter6000:rate-num" {
    deviate replace {
      type uint32 {
        range "0..100000000";
      }
    }
  }

  /*change queue min burst from "1000..524288" to "4096..2093056"*/
  deviation "/qosrouter6000:qos/qosrouter6000:policy/qosrouter6000:policy-choice/qosrouter6000:pwfq/qosrouter6000:pwfq/qosrouter6000:queue/qosrouter6000:queue-choice/"
  + "qosrouter6000:rate/qosrouter6000:rate-choice/qosrouter6000:minimum-guarantee/qosrouter6000:minimum-guarantee-choice/qosrouter6000:rate-num/qosrouter6000:rate-num/qosrouter6000:burst" {
    deviate replace {
      type uint32 {
        range "4096..2093056";
      }
    }
  }

  /*change range from "1000..524288" to "4096..2093056"*/
  deviation "/qosrouter6000:qos/qosrouter6000:policy/qosrouter6000:policy-choice/qosrouter6000:pwfq/qosrouter6000:pwfq/qosrouter6000:queue/qosrouter6000:queue-choice/"
  + "qosrouter6000:rate/qosrouter6000:rate-choice/qosrouter6000:maximum/qosrouter6000:maximum-choice/qosrouter6000:rate-num/qosrouter6000:rate-num/qosrouter6000:burst" {
     deviate replace {
      type uint32 {
        range "4096..2093056";
      }
    }
  }

  /*change queue max rate from "0..10000000" to "0..100000000"*/
  deviation "/qosrouter6000:qos/qosrouter6000:policy/qosrouter6000:policy-choice/qosrouter6000:pwfq/qosrouter6000:pwfq/qosrouter6000:queue/qosrouter6000:queue-choice/"
  + "qosrouter6000:rate/qosrouter6000:rate-choice/qosrouter6000:maximum/qosrouter6000:maximum-choice/qosrouter6000:rate-num/qosrouter6000:rate-num/qosrouter6000:rate-num" {
    deviate replace {
      type uint32 {
        range "0..100000000";
      }
    }
  }

  /*change range from "325..10000000" to "1171..10000000"*/
  deviation "/qosrouter6000:qos/qosrouter6000:policy/qosrouter6000:policy-choice/qosrouter6000:pwfq/qosrouter6000:pwfq/qosrouter6000:rate/qosrouter6000:pir/qosrouter6000:rate-num" {
     deviate replace {
      type uint32 {
        range "1171..100000000";
      }
    }
  }

  /*change range from "1000..524288" to "4096..2093056"*/
  deviation "/qosrouter6000:qos/qosrouter6000:policy/qosrouter6000:policy-choice/qosrouter6000:pwfq/qosrouter6000:pwfq/qosrouter6000:rate/qosrouter6000:pir/qosrouter6000:burst" {
     deviate replace {
      type uint32 {
        range "4096..2093056";
      }
      default "16384";
    }
  }

  /*R6676:change range from "325..10000000" to "1171..10000000"*/
  deviation "/qosrouter6000:qos/qosrouter6000:policy/qosrouter6000:policy-choice/qosrouter6000:pwfq/qosrouter6000:pwfq/qosrouter6000:rate/qosrouter6000:cir/qosrouter6000:rate-num" {
     deviate replace {
      type uint32 {
        range "1171..100000000";
      }
    }
  }

  /*change range from "1000..524288" to "4096..2093056"*/
  deviation "/qosrouter6000:qos/qosrouter6000:policy/qosrouter6000:policy-choice/qosrouter6000:pwfq/qosrouter6000:pwfq/qosrouter6000:rate/qosrouter6000:cir/qosrouter6000:burst" {
     deviate replace {
      type uint32 {
        range "4096..2093056";
      }
      default "16384";
    }
  }

  /*ip-access-group*/
  /*global->QoS->policy->policing->ip-access-group->acl-class*->rate->rate-num*/
  /*R6676:change range from "5..10000000" to "22..300000000"*/
  deviation "/qosrouter6000:qos/qosrouter6000:policy/qosrouter6000:policy-choice/qosrouter6000:policing/qosrouter6000:policing/qosrouter6000:ip-access-group"
  + "/qosrouter6000:acl-class/qosrouter6000:rate/qosrouter6000:rate-choice/qosrouter6000:rate-num/qosrouter6000:rate-num/qosrouter6000:rate-num" {
    deviate replace {
      type uint32 {
        range "22..300000000";
      }
    }
  }

  /*global->QoS->policy->policing->ip-access-group->acl-class*->rate->burst*/
  /*change range from "0..33292" to "125..4000000"*/
  deviation "/qosrouter6000:qos/qosrouter6000:policy/qosrouter6000:policy-choice/qosrouter6000:policing/qosrouter6000:policing/qosrouter6000:ip-access-group"
  + "/qosrouter6000:acl-class/qosrouter6000:rate/qosrouter6000:rate-choice/qosrouter6000:rate-num/qosrouter6000:rate-num/qosrouter6000:burst" {
    deviate replace {
      type int32 {
        range "125..4000000";
      }
    }
  }

  /*global->QoS->policy->policing->ip-access-group->acl-class*->rate->excess-burst*/
  /*change range from "0..33292" to "125..4000000"*/
  deviation "/qosrouter6000:qos/qosrouter6000:policy/qosrouter6000:policy-choice/qosrouter6000:policing/qosrouter6000:policing/qosrouter6000:ip-access-group"
  + "/qosrouter6000:acl-class/qosrouter6000:rate/qosrouter6000:rate-choice/qosrouter6000:rate-num/qosrouter6000:rate-num/qosrouter6000:excess-burst" {
    deviate replace {
      type int32 {
        range "125..4000000";
      }
    }
  }

  /*ipv6-access-group*/
  /*global->QoS->policy->policing->ipv6-access-group->acl-class*->rate->rate-num*/
  /*R6672:change range from "5..10000000" to "20..300000000"*/
  deviation "/qosrouter6000:qos/qosrouter6000:policy/qosrouter6000:policy-choice/qosrouter6000:policing/qosrouter6000:policing/qosrouter6000:ipv6-access-group"
  + "/qosrouter6000:acl-class/qosrouter6000:rate/qosrouter6000:rate-choice/qosrouter6000:rate-num/qosrouter6000:rate-num/qosrouter6000:rate-num" {
    deviate replace {
      type uint32 {
        range "22..300000000";
      }
    }
  }

  /*global->QoS->policy->policing->ipv6-access-group->acl-class*->rate->burst*/
  /*change range from "0..33292" to "125..4000000"*/
  deviation "/qosrouter6000:qos/qosrouter6000:policy/qosrouter6000:policy-choice/qosrouter6000:policing/qosrouter6000:policing/qosrouter6000:ipv6-access-group"
  + "/qosrouter6000:acl-class/qosrouter6000:rate/qosrouter6000:rate-choice/qosrouter6000:rate-num/qosrouter6000:rate-num/qosrouter6000:burst" {
    deviate replace {
      type int32 {
        range "125..4000000";
      }
    }
  }

  /*global->QoS->policy->policing->ipv6-access-group->acl-class*->rate->excess-burst*/
  /*change range from "0..33292" to "125..4000000"*/
  deviation "/qosrouter6000:qos/qosrouter6000:policy/qosrouter6000:policy-choice/qosrouter6000:policing/qosrouter6000:policing/qosrouter6000:ipv6-access-group"
  + "/qosrouter6000:acl-class/qosrouter6000:rate/qosrouter6000:rate-choice/qosrouter6000:rate-num/qosrouter6000:rate-num/qosrouter6000:excess-burst" {
    deviate replace {
      type int32 {
        range "125..4000000";
      }
    }
  }

  /*L2-access-group*/
  /*global->QoS->policy->policing->l2-access-group->acl-class*->rate->rate-num*/
  /*R6676:change range from "5..10000000" to "22..300000000"*/
  deviation "/qosrouter6000:qos/qosrouter6000:policy/qosrouter6000:policy-choice/qosrouter6000:policing/qosrouter6000:policing/qosrouter6000:l2-access-group"
  + "/qosrouter6000:acl-class/qosrouter6000:rate/qosrouter6000:rate-choice/qosrouter6000:rate-num/qosrouter6000:rate-num/qosrouter6000:rate-num" {
    deviate replace {
      type uint32 {
        range "22..300000000";
      }
    }
  }

  /*global->QoS->policy->policing->l2-access-group->acl-class*->rate->burst*/
  /*change range from "0..33292" to "125..4000000"*/
  deviation "/qosrouter6000:qos/qosrouter6000:policy/qosrouter6000:policy-choice/qosrouter6000:policing/qosrouter6000:policing/qosrouter6000:l2-access-group"
  + "/qosrouter6000:acl-class/qosrouter6000:rate/qosrouter6000:rate-choice/qosrouter6000:rate-num/qosrouter6000:rate-num/qosrouter6000:burst" {
    deviate replace {
      type int32 {
        range "125..4000000";
      }
    }
  }

  /*global->QoS->policy->policing->l2-access-group->acl-class*->rate->excess-burst*/
  /*change range from "0..33292" to "125..4000000"*/
  deviation "/qosrouter6000:qos/qosrouter6000:policy/qosrouter6000:policy-choice/qosrouter6000:policing/qosrouter6000:policing/qosrouter6000:l2-access-group"
  + "/qosrouter6000:acl-class/qosrouter6000:rate/qosrouter6000:rate-choice/qosrouter6000:rate-num/qosrouter6000:rate-num/qosrouter6000:excess-burst" {
    deviate replace {
      type int32 {
        range "125..4000000";
      }
    }
  }

  /*class-group*/
  /*global->QoS->policy->policing->class-group->acl-class*->rate->rate-num*/
  /*R6676:change range from "5..10000000" to "22..300000000"*/
  deviation "/qosrouter6000:qos/qosrouter6000:policy/qosrouter6000:policy-choice/qosrouter6000:policing/qosrouter6000:policing/qosrouter6000:class-group"
  + "/qosrouter6000:class/qosrouter6000:rate/qosrouter6000:rate-choice/qosrouter6000:rate-num/qosrouter6000:rate-num/qosrouter6000:rate-num" {
    deviate replace {
      type uint32 {
        range "22..300000000";
      }
    }
  }

  /*global->QoS->policy->policing->class-group->acl-class*->rate->burst*/
  /*change range from "0..33292" to "125..4000000"*/
  deviation "/qosrouter6000:qos/qosrouter6000:policy/qosrouter6000:policy-choice/qosrouter6000:policing/qosrouter6000:policing/qosrouter6000:class-group"
  + "/qosrouter6000:class/qosrouter6000:rate/qosrouter6000:rate-choice/qosrouter6000:rate-num/qosrouter6000:rate-num/qosrouter6000:burst" {
    deviate replace {
      type int32 {
        range "125..4000000";
      }
    }
  }

  /*global->QoS->policy->policing->class-group->acl-class*->rate->excess-burst*/
  /*change range from "0..33292" to "125..4000000"*/
  deviation "/qosrouter6000:qos/qosrouter6000:policy/qosrouter6000:policy-choice/qosrouter6000:policing/qosrouter6000:policing/qosrouter6000:class-group"
  + "/qosrouter6000:class/qosrouter6000:rate/qosrouter6000:rate-choice/qosrouter6000:rate-num/qosrouter6000:rate-num/qosrouter6000:excess-burst" {
    deviate replace {
      type int32 {
        range "125..4000000";
      }
    }
  }

}
