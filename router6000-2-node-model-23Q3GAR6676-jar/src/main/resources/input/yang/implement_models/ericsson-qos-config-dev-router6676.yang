module ericsson-qos-config-dev-router6676 {
  yang-version "1";

  namespace "urn:rdns:com:ericsson:oammodel:ericsson-qos-config-dev-router6676";

  prefix "qoscfgrouter6676";

  import ericsson-inner-port-router6000 {
    prefix "innerportrouter6000";
  }

  import ericsson-qos-config-router6000 {
    prefix "qoscfgr6k";
  }

  import ericsson-contexts-router6000 {
    prefix "ctxsr6k";
  }

  import ericsson-context-router6000 {
    prefix "ctxr6k";
  }

  import ericsson-mpls-router6000 {
    prefix "mplsr6k";
  }

  import ericsson-yang-extensions {
    prefix "yexte";
  }

  organization
    "Ericsson AB";

  contact
    "Web:   <http://www.ericsson.com>";

  description
    "ericsson-qos-config-dev-router6676
     Copyright (c) 2020 Ericsson AB.
     All rights reserved";


  revision "2022-10-31" {
    description
      "add internal port for max bandwidth";
    reference
      "rfc6020";
    yexte:version "1";
    yexte:release "1";
    yexte:correction "0";
  }

  revision "2020-12-03" {
    description
      "deviation for to mpls l2vpn classmap.";
    reference
      "rfc6020";
    yexte:version "1";
    yexte:release "0";
    yexte:correction "0";
  }


  deviation "/ctxsr6k:contexts/ctxr6k:context/ctxr6k:router/mplsr6k:mpls/mplsr6k:propagate/qoscfgr6k:qos/qoscfgr6k:to/qoscfgr6k:mpls/qoscfgr6k:class-map-option/qoscfgr6k:l2vpn-class-map" {
     deviate not-supported;
  }

  deviation "/ctxsr6k:contexts/innerportrouter6000:recycling-card/innerportrouter6000:inter-context-routing/innerportrouter6000:bandwidth" {
    deviate replace {
      type uint32 {
        range "1000000..180000000";
      }
    }
  }

  deviation "/ctxsr6k:contexts/innerportrouter6000:recycling-card/innerportrouter6000:mvpn-bud/innerportrouter6000:bandwidth" {
    deviate replace {
      type uint32 {
        range "1000000..180000000";
      }
    }
  }

  deviation "/ctxsr6k:contexts/innerportrouter6000:recycling-card/innerportrouter6000:egress-mirror/innerportrouter6000:bandwidth" {
    deviate replace {
      type uint32 {
        range "1000000..180000000";
      }
    }
  }

  deviation "/ctxsr6k:contexts/innerportrouter6000:recycling-card/innerportrouter6000:DSCP-Remark/innerportrouter6000:bandwidth" {
    deviate replace {
      type uint32 {
        range "1000000..180000000";
      }
    }
  }

  deviation "/ctxsr6k:contexts/innerportrouter6000:ethernet-oam-throughput-card/innerportrouter6000:bandwidth-value" {
    deviate replace {
      type uint32 {
        range "1000000..180000000";
      }
    }
  }

}
