module ericsson-isis-router6000 {
  yang-version "1";

  namespace "urn:rdns:com:ericsson:oammodel:ericsson-isis-router6000";

  prefix "isisrouter6000";

  import ietf-inet-types {
    prefix "inet";
  }

  import ietf-interfaces {
    prefix "if";
  }

  import ericsson-types-router6000 {
    prefix "typesrouter6000";
  }

  import ericsson-contexts-router6000 {
    prefix "ctxsr6k";
  }

  import ericsson-context-router6000 {
    prefix "ctxr6k";
  }

  import ericsson-yang-extensions {
    prefix "yexte";
  }

  organization
    "Ericsson AB";

  contact
    "Web:   <http://www.ericsson.com>";

  description
    "ericsson-isis-router6000
     Copyright (c) 2023 Ericsson AB.
     All rights reserved";

  revision "2023-04-10" {
    description
      "Modify isis net id into list";
    reference
      "rfc6020";
    yexte:version "3";
    yexte:release "11";
    yexte:correction "0";
  }

  revision "2023-03-30" {
    description
      "Extended SRGB range";
    reference
      "rfc6020";
    yexte:version "3";
    yexte:release "10";
    yexte:correction "0";
  }

  revision "2022-05-22" {
    description
      "Add a new command for adjacency-sid srv6";
    reference
      "rfc6020";
    yexte:version "3";
    yexte:release "9";
    yexte:correction "0";
  }

  revision "2022-02-14" {
    description
      "Add a new command for adjacency-sid srv6";
    reference
      "rfc6020";
    yexte:version "3";
    yexte:release "8";
    yexte:correction "6";
  }

  revision "2022-02-09" {
    description
      "fix for isis nbc issue";
    reference
      "rfc6020";
    yexte:version "3";
    yexte:release "8";
    yexte:correction "5";
  }

  revision "2022-02-04" {
    description
      "Add locators under interface sids";
    reference
      "rfc6020";
    yexte:version "3";
    yexte:release "8";
    yexte:correction "4";
  }

  revision "2022-02-02" {
    description
      "Modify level under locator token";
    reference
      "rfc6020";
    yexte:version "3";
    yexte:release "8";
    yexte:correction "3";
  }

  revision "2022-01-27" {
    description
      "fix for isis nbc issue";
    reference
      "rfc6020";
    yexte:version "3";
    yexte:release "8";
    yexte:correction "2";
  }

  revision "2022-01-25" {
    description
      "fix for validation error";
    reference
      "rfc6020";
    yexte:version "3";
    yexte:release "8";
    yexte:correction "1";
  }

  revision "2021-12-20" {
    description
      "add srv6 chain";
    reference
      "rfc6020";
    yexte:version "3";
    yexte:release "8";
    yexte:correction "0";
  }

  revision "2021-10-18" {
    description
      "fix for ipv6 summary-address";
    reference
      "rfc6020";
    yexte:version "3";
    yexte:release "7";
    yexte:correction "1";
  }

  revision "2021-07-23" {
    description
      "Add multi-topology transition [exclude-mt-tlvs] CLI";
    reference
      "rfc6020";
    yexte:version "3";
    yexte:release "7";
    yexte:correction "0";
  }

  revision "2021-06-02" {
    description
      "libnetconf2 issue fix";
    reference
      "rfc6020";
    yexte:version "3";
    yexte:release "6";
    yexte:correction "0";
  }

  revision "2021-05-02" {
    description
      "R6K-2108 Changing the leaf vpn-rd to vpn-conf,since the
       leaf vpn-rd is obsoleted";
    reference
      "rfc6020";
    yexte:version "3";
    yexte:release "5";
    yexte:correction "1";
  }

  revision "2021-02-09" {
    description
      "Support RFC 5310 Generic crypto hmac-sha1/sha2
       authentication";
    reference
      "rfc6020";
    yexte:version "3";
    yexte:release "5";
    yexte:correction "0";
  }

  revision "2021-02-03" {
    description
      "Support for ISIS SR MPLS IPv6";
    reference
      "rfc6020";
    yexte:version "3";
    yexte:release "4";
    yexte:correction "0";
  }

  revision "2020-12-14" {
    description
      "Added route tag for summary-address and interaface
       commands";
    reference
      "rfc6020";
    yexte:version "3";
    yexte:release "3";
    yexte:correction "0";
  }

  revision "2020-11-10" {
    description
      "Adding a configuration command for enabling/disabling
       hello packet logging with padding";
    reference
      "exec_cli";
    yexte:version "3";
    yexte:release "2";
    yexte:correction "0";
  }

  revision "2020-03-11" {
    description
      "obsolete the prefix-sid-index and add
       prefix-sid-conf-index container";
    reference
      "rfc6020";
    yexte:version "3";
    yexte:release "1";
    yexte:correction "6";
  }

  revision "2020-02-20" {
    description
      "Updated prefix-sid range according to new SRGB range";
    reference
      "rfc6020";
    yexte:version "3";
    yexte:release "1";
    yexte:correction "5";
  }

  revision "2020-01-23" {
    description
      "Added new range for segment-routing-global-block";
    reference
      "rfc6020";
    yexte:version "3";
    yexte:release "1";
    yexte:correction "4";
  }

  revision "2018-11-27" {
    description
      "remove ipos choice description";
    reference
      "rfc6020";
    yexte:version "3";
    yexte:release "1";
    yexte:correction "3";
  }

  revision "2018-09-20" {
    description
      "CLI changes for adding node protection option to ti-lfa
       cli.";
    reference
      "rfc6020";
    yexte:version "3";
    yexte:release "1";
    yexte:correction "2";
  }

  revision "2018-08-14" {
    description
      "IPOS-25528 TI-LFA Netconf issue Can't get command ti-lfa
       protect node-only segment-limit 2 from node";
    reference
      "rfc6020";
    yexte:version "3";
    yexte:release "1";
    yexte:correction "1";
  }

  revision "2018-07-12" {
    description
      "Removing preliminary tag for ISIS feature ti-lfa node and
       adj sid protection";
    reference
      "rfc6020";
    yexte:version "3";
    yexte:release "1";
    yexte:correction "0";
  }

  revision "2018-06-05" {
    description
      "Change model namespace";
    reference
      "rfc6020";
    yexte:version "3";
    yexte:release "0";
    yexte:correction "0";
  }

  revision "2018-05-03" {
    description
      "add when condition to restrict adjacency-sid and
       prefix-sid;delete redundent must condition on interface
       and isis token";
    reference
      "exec_cli";
    yexte:version "2";
    yexte:release "0";
    yexte:correction "1";
  }

  revision "2018-02-06" {
    description
      "level option is deleted in the link-state id CLI under
       ISIS.";
    reference
      "rfc7752";
    yexte:version "2";
    yexte:release "0";
    yexte:correction "0";
  }

  revision "2018-01-02" {
    description
      "JIRA:SSR-6748 Added App-ID for LIM Application Id for LIM
       feature.";
    reference
      "rfc6020";
    yexte:version "1";
    yexte:release "4";
    yexte:correction "0";
  }

  revision "2017-12-30" {
    description
      "IPOS 7880 move microloop-delay cmd under AF mode and
       modify it`s upper-limit value to 15 seconds";
    reference
      "rfc6020";
    yexte:version "1";
    yexte:release "3";
    yexte:correction "0";
  }

  revision "2017-12-18" {
    description
      "VRE 2366 Adding redistribute seg and service
       fabric-hello-interval yang commands";
    reference
      "rfc6020";
    yexte:version "1";
    yexte:release "2";
    yexte:correction "0";
  }

  revision "2017-12-15" {
    description
      "IPOS 7880 Micro-loop feature configuration";
    reference
      "rfc6020";
    yexte:version "1";
    yexte:release "1";
    yexte:correction "0";
  }

  revision "2017-11-07" {
    description
      "add new container metricpassive for passive interface
       only";
    reference
      "exec cli";
    yexte:version "1";
    yexte:release "0";
    yexte:correction "3";
  }

  revision "2017-08-10" {
    description
      "add when condition to restrict adjacency-sid and
       prefix-sid,they are not executable under a vpn context";
    reference
      "rfc6020";
    yexte:version "1";
    yexte:release "0";
    yexte:correction "2";
  }

  revision "2017-07-25" {
    description
      "add when condition on container adjacency-sid and
       confainer prefix-sid";
    reference
      "rfc6020";
    yexte:version "1";
    yexte:release "0";
    yexte:correction "1";
  }

  revision "2017-07-13" {
    description
      "add cf_flag for snmp traps";
    reference
      "rfc6020";
    yexte:version "1";
    yexte:release "0";
    yexte:correction "0";
  }

  revision "2017-06-26" {
    description
      "delete if-feature lfa_spf,delete if-feature
       segment-routing,modify container snmp-traps";
    reference
      "rfc6020";
  }

  revision "2017-06-05" {
    description
      "add when condition on lfa and remote-lfa;add new
       container snmp,add new leaf
       unidirectional-available-bandwidth,add new leaf
       unidirectional-link-delay";
    reference
      "rfc6020";
  }

  revision "2017-05-31" {
    description
      "IPOS-10643 and IPOS-10974:modify segment-routing
       command;redistribute application add if-feature";
    reference
      "rfc6020";
  }

  revision "2017-05-27" {
    description
      " TI LFA feature configuration";
    reference
      "draft-bashandy-rtgwg-segment-routing-ti-lfa-00";
  }

  revision "2017-03-28" {
    description
      "change segment-routing-global-block to list;add new
       command";
    reference
      "rfc6020";
  }

  revision "2017-03-09" {
    description
      "IPOS-7763 retransmit-interval in ISIS model should keep
       the previous type as uint16";
    reference
      "rfc6020";
  }

  revision "2017-01-18" {
    description
      "HV HV53277:removing if-feature 'if_srlg' in isis-ipos
       yang file;split address-family ipv4 and ipv6";
    reference
      "rfc6020";
  }

  revision "2017-01-04" {
    description
      "Fix side-effect";
    reference
      "rfc6020";
  }

  revision "2016-12-05" {
    description
      "add support for remote lfa feature";
    reference
      "rfc6020";
  }

  revision "2016-10-28" {
    description
      "Delete if-feature for lfa";
    reference
      "rfc6020";
  }

  revision "2016-03-29" {
    description
      "For CLI2Yang models data node sequence change.";
    reference
      "rfc6020";
  }

  revision "2015-12-07" {
    description
      "initial revision";
    reference
      "rfc6020";
  }

  feature nonstop-routing {
    description
      "This feature indicates that the device supports
       nonstop-routing in IS-IS.";
  }

  feature if_af_ipv4_multicast {
    description
      "This feature indicates that the device supports IPv4
       multicast on IS-IS interface in IS-IS.";
  }

  feature if_af_ipv6_multicast {
    description
      "This feature indicates that the device supports IPv6
       multicast on IS-IS interface in IS-IS.";
  }

  feature af_ipv4_multicast {
    description
      "This feature indicates that the device supports IPv4
       multicast topology on an IS-IS instance in IS-IS.";
  }

  feature af_ipv6_multicast {
    description
      "This feature indicates that the device supports IPv6
       multicast topology on an IS-IS instance in IS-IS.";
  }

  feature af_redis_bgf {
    description
      "This feature indicates that the device supports to
       redistribute information from Border Gateway Function
       (BGF) in IS-IS.";
  }

  feature af_redis_cgnat {
    description
      "This feature indicates that the device supports to
       redistribute information from Carrier Grade Network
       Address Translation (CGNAT) in IS-IS.";
  }

  feature af_redis_epg {
    description
      "This feature indicates that the device supports to
       redistribute information from Evolved Packet Gateway (EPG)
       routes in IS-IS.";
  }

  feature af_redis_ipsec {
    description
      "This feature indicates that the device supports to
       redistribute information from IPsec routes in IS-IS.";
  }

  feature af_redis_msp {
    description
      "This feature indicates that the device supports to
       redistribute information from Multi-Service Proxy (MSP)
       routes in IS-IS.";
  }

  feature af_redis_nat {
    description
      "This feature indicates that the device supports to
       redistribute information from Network Address Translation
       (NAT) in IS-IS.";
  }

  feature af_ipv4_redis_rip {
    description
      "This feature indicates that the device supports to
       redistribute information from RIP routes for IPv4 unicast
       topology in IS-IS.";
  }

  feature af_ipv6_redis_rip {
    description
      "This feature indicates that the device supports to
       redistribute information from RIP routes for IPv6 unicast
       topology in IS-IS.";
  }

  feature af_redis_sasn {
    description
      "This feature indicates that the device supports to
       redistribute information from Service-Aware Support Node
       (SASN) routes in IS-IS.";
  }

  feature af_ipv4_redis_subscriber {
    description
      "This feature indicates that the device supports to
       redistribute information from Subscriber routes for IPv4
       unicast topology in IS-IS.";
  }

  feature af_ipv6_redis_subscriber {
    description
      "This feature indicates that the device supports to
       redistribute information from Subscriber routes for IPv6
       unicast topology in IS-IS.";
  }

  feature af_redis_vrrp {
    description
      "This feature indicates that the device supports to
       redistribute information from Virtual Router Redundancy
       (VRRP) routes in IS-IS.";
  }

  feature af_redis_wifiac {
    description
      "This feature indicates that the device supports to
       redistribute information from WiFi Access Concentrator
       (WiFiAC) routes in IS-IS.";
  }

  feature af_redis_wmg {
    description
      "This feature indicates that the device supports to
       redistribute information from Wi-Fi Mobility Gateway (WMG)
       routes in IS-IS.";
  }

  feature af_seg_rt {
    description
      "This feature indicates that the device supports segment
       routing in IS-IS.";
  }

  feature af_redis_seg {
    description
      "This feature indicates that the device supports to
       redistribute information from Security Gateway (SEG)
       routes in IS-IS.";
  }

  feature af_redis_app {
    description
      "This feature indicates that the device supports to
       redistribute information from application sgsn-mme routes
       in IS-IS.";
  }

  grouping isis-if-grp {
    description
      "ISIS interface configuration mode";
    /*
    authentication { (level-1) | (level-2) } { key-chain
     (keychain-name) } [ type { hmac-md5 | simple | hmac-
     cryptographic } ] [no-check]
    */
    list authentication {
      key "authentication-choice";
      description
        "Configure authentication for hello packets";
      leaf authentication-choice {
        type enumeration {
          enum level-1 {
            value 0;
            description
              "Configure authentication on level-1 IIHs";
          }
          enum level-2 {
            value 1;
            description
              "Configure authentication on level-2 IIHs";
          }
        }
        description
          "leaf authentication-choice.";
      }
      leaf key-chain {
        type string;
        mandatory true;
        description
          "Configure authentication using key-chain";
      }
      leaf type {
        type enumeration {
          enum hmac-md5 {
            value 0;
            description
              "Configure authentication type hmac-md5(default)";
          }
          enum simple {
            value 1;
            description
              "Configure authentication type simple";
          }
          enum hmac-cryptographic {
            value 2;
            description
              "Configure authentication type hmac-cryptographic";
          }
        }
        default "hmac-md5";
        description
          "Configure authentication type";
      }
      leaf no-check {
        type empty;
        description
          "Configure ignoring authentication on receive";
      }
    }
    /*
    circuit { mtu (mtu-num) | type { level-1 | level-2-only |
     level-1-2 } }
    */
    container circuit {
      description
        "Set IS-IS circuit parameters";
      leaf mtu {
        type uint16 {
          range "256..9140";
        }
        description
          "Configure circuit isis mtu";
      }
      leaf type {
        type enumeration {
          enum level-1 {
            value 0;
            description
              "Set circuit to level-1 only type";
          }
          enum level-2-only {
            value 1;
            description
              "Set circuit to level-2 only type";
          }
          enum level-1-2 {
            value 2;
            description
              "Set circuit to level-1 and level-2 type(default)";
          }
        }
        default "level-1-2";
        description
          "Configure circuit type for IS-IS interface";
      }
    }
    /*
    csnp { { { interval level-1 } (interval-value) } | { {
     interval level-2 } (interval-value) } | periodic-on-ptp }
    */
    container csnp {
      description
        "Set CSNP parameters on IS-IS interface";
      leaf interval-level-1 {
        type uint16 {
          range "1..65535";
        }
        default "10";
        description
          "Set CSNP interval on LAN in seconds";
      }
      leaf interval-level-2 {
        type uint16 {
          range "1..65535";
        }
        default "10";
        description
          "Set CSNP interval on LAN in seconds";
      }
      leaf periodic-on-ptp {
        type empty;
        description
          "Issue periodic csnps on point-to-point interface";
      }
    }
    /*
    hello { { { interval level-1 } (interval-value) } | { {
     interval level-2 } (interval-value) } | { { multiplier
     level-1 } (multiplier-value) } | { { multiplier level-2 }
     (multiplier-value) } | padding { first-only | never | always
     } }
    */
    container hello {
      description
        "Set IS-IS interface IIH parameters";
      leaf interval-level-1 {
        type uint16 {
          range "1..65535";
        }
        default "10";
        description
          "Set IS-IS Hello interval";
      }
      leaf interval-level-2 {
        type uint16 {
          range "1..65535";
        }
        default "10";
        description
          "Set IS-IS Hello interval";
      }
      leaf multiplier-level-1 {
        type uint16 {
          range "3..1000";
        }
        default "3";
        description
          "Set Hello multiplier";
      }
      leaf multiplier-level-2 {
        type uint16 {
          range "3..1000";
        }
        default "3";
        description
          "Set Hello multiplier";
      }
      leaf padding {
        type enumeration {
          enum first-only {
            value 0;
            description
              "Only initial hellos padded to MTU (default)";
          }
          enum never {
            value 1;
            description
              "Never pad hellos to MTU size";
          }
          enum always {
            value 2;
            description
              "Always pad hellos to MTU size";
          }
        }
        default "first-only";
        description
          "Set Hello padding style";
      }
    }
    /*
    lsp { interval (interval-value) | receive-only-mode | block-
     flooding { (level-1) | (level-2) } | retransmit-interval
     (interval-value) }
    */
    container lsp {
      description
        "Set LSP parameters on the IS-IS interface";
      leaf interval {
        type uint16 {
          range "10..65535";
        }
        description
          "Set LSP transmission interval";
      }
      leaf receive-only-mode {
        type empty;
        description
          "For testing purpose, never send LSP out on this
           circuit";
      }
      list block-flooding {
        key "block-flooding";
        max-elements 2;
        description
          "Stop flooding of LSPs on this interface";
        leaf block-flooding {
          type enumeration {
            enum level-1 {
              value 0;
              description
                "Stop flooding for level-1 only";
            }
            enum level-2 {
              value 1;
              description
                "Stop flooding for level-2 only";
            }
          }
          description
            "leaf block-flooding.";
        }
      }
      leaf retransmit-interval {
        type uint16 {
          range "1..120";
        }
        default "5";
        description
          "Set per-LSP retransmission interval";
      }
    }
    /*
    optional-checksums { level-1 | level-2 }
    */
    list optional-checksums {
      key "optional-checksums";
      max-elements 2;
      description
        "Add optional checksums to hellos and snps";
      leaf optional-checksums {
        type enumeration {
          enum level-1 {
            value 0;
            description
              "Stop checksum for level-1 only";
          }
          enum level-2 {
            value 1;
            description
              "Stop checksum for level-2 only";
          }
        }
        description
          "leaf optional-checksums.";
      }
    }
    /*
    passive-interface
    */
    leaf passive-interface {
      type empty;
      description
        "Suppress routing updates on an interface";
    }
    /*
    priority { level-1 (priority-value) | level-2 (priority-
     value) }
    */
    container priority {
      description
        "Set priority for Designated Router election";
      leaf level-1 {
        type uint8 {
          range "0..127";
        }
        default "64";
        description
          "Configure priority value for level-1 only";
      }
      leaf level-2 {
        type uint8 {
          range "0..127";
        }
        default "64";
        description
          "Configure priority value for level-2 only";
      }
    }
    /*
    ldp-igp-synchronization
    */
    leaf ldp-igp-synchronization {
      type boolean;
      default "true";
      description
        "Enable/Disable ldp-igp-synchronization";
    }
    /*
    srlg (srlg-spec)
    */
    leaf srlg {
      type uint32 {
        range "0..4294967295";
      }
      description
        "Configure interface Shared Risk Link Group (SRLG)";
    }
    /*
    unidirectional-available-bandwidth (bandwidth-spec)
    */
    leaf unidirectional-available-bandwidth {
      type uint32 {
        range "0..4294967295";
      }
      description
        "Configure Unidirectional Available Bandwidth";
    }
    /*
    unidirectional-link-delay (delay-spec)
    */
    leaf unidirectional-link-delay {
      type uint32 {
        range "0..16777215";
      }
      description
        "Configure Unidirectional Link Delay";
    }
    /*
    address-family { ipv4 { unicast | multicast } | ipv6 {
     unicast | multicast } | ipv4-conf { unicast | multicast } }
    */
    container address-family {
      description
        "Enable IS-IS for an address-family/topology";
      container ipv4 {
        status obsolete;
        description
          "Enable IS-IS for IPv4";
        container unicast {
          description
            "Enable IS-IS for IPv4 unicast topology";
          leaf unicast-enable {
            type boolean;
            default "true";
            description
              "Enable/Disable unicast-enable";
          }
          uses isis-if-af-grp;
        }
        container multicast {
          if-feature if_af_ipv4_multicast;
          presence "";
          description
            "Enable IS-IS for IPv4 multicast topology";
          uses isis-if-af-grp;
        }
      }
      container ipv6 {
        description
          "Enable IS-IS for IPv6";
        container unicast {
          presence "";
          description
            "Enable IS-IS for IPv6 unicast topology";
          uses isis-if-af-grp;
        }
        container multicast {
          if-feature if_af_ipv6_multicast;
          presence "";
          description
            "Enable IS-IS for IPv6 multicast topology";
          uses isis-if-af-grp;
        }
      }
      container ipv4-conf {
        description
          "Enable IS-IS for IPv4";
        container unicast {
          presence "";
          description
            "Enable IS-IS for IPv4 unicast topology";
          leaf unicast-enable {
            type boolean;
            default "true";
            description
              "Enable/Disable unicast-enable";
          }
          uses isis-if-af-grp;
        }
        container multicast {
          if-feature if_af_ipv4_multicast;
          presence "";
          description
            "Enable IS-IS for IPv4 multicast topology";
          uses isis-if-af-grp;
        }
      }
    }
    /*
    log-hello-packet include-padding
    */
    leaf log-hello-packet-include-padding {
      type empty;
      description
        "Hello packet logging with padding";
    }
  }

  grouping isis-grp {
    description
      "ISIS configuration mode";
    /*
    attached-bit { ignore | never-set }
    */
    container attached-bit {
      description
        "Configure L1 LSP attached-bit preference";
      leaf ignore {
        type empty;
        description
          "Ignore the attached flag in L1 LSPs";
      }
      leaf never-set {
        type empty;
        description
          "Do not set the attached flag in L1 LSPs";
      }
    }
    /*
    authentication { (level-1) | (level-2) } { key-chain
     (keychain-name) } [ type { hmac-md5 | simple | hmac-
     cryptographic } ] [lsp-only] [no-check]
    */
    list authentication {
      key "authentication-choice";
      description
        "Configure authentication for isis packets";
      leaf authentication-choice {
        type enumeration {
          enum level-1 {
            value 0;
            description
              "Configure authentication on level-1 area";
          }
          enum level-2 {
            value 1;
            description
              "Configure authentication on level-2 domain";
          }
        }
        description
          "leaf authentication-choice.";
      }
      leaf key-chain {
        type string;
        mandatory true;
        description
          "Configure authentication using key-chain";
      }
      leaf type {
        type enumeration {
          enum hmac-md5 {
            value 0;
            description
              "Configure authentication type hmac-md5(default)";
          }
          enum simple {
            value 1;
            description
              "Configure authentication type simple";
          }
          enum hmac-cryptographic {
            value 2;
            description
              "Configure authentication type hmac-cryptographic";
          }
        }
        default "hmac-md5";
        description
          "Configure authentication type";
      }
      leaf lsp-only {
        type empty;
        description
          "Configure authentication on LSP only";
      }
      leaf no-check {
        type empty;
        description
          "Configure ignoring authentication on receive";
      }
    }
    /*
    distance (distance-value)
    */
    leaf distance {
      type uint8 {
        range "1..255";
      }
      default "115";
      description
        "Define an administrative distance";
    }
    /*
    dynamic-hostname [ display | router-name (hostname-string) ]
    */
    container dynamic-hostname {
      description
        "Configure dynamic hostname advertisement";
      leaf dynamic-hostname-enable {
        type boolean;
        default "true";
        description
          "Enable/Disable dynamic-hostname-enable";
      }
      leaf display {
        when "../dynamic-hostname-enable='true'" {
          description
            "";
        }
        type empty;
        description
          "Enable dynamic hostname display only";
      }
      leaf router-name {
        when "../dynamic-hostname-enable='true'" {
          description
            "";
        }
        type string;
        description
          "Router name for the instance";
      }
    }
    /*
    is type { level-1 | level-2-only | level-1-2 }
    */
    container is {
      description
        "Set IS-IS system parameters";
      leaf type {
        type enumeration {
          enum level-1 {
            value 0;
            description
              "IS-IS level-1 only type";
          }
          enum level-2-only {
            value 1;
            description
              "IS-IS level-2 only type";
          }
          enum level-1-2 {
            value 2;
            description
              "IS-IS level-1 and level-2 type";
          }
        }
        default "level-1-2";
        description
          "Levels ISIS participates in";
      }
    }
    /*
    lsp { { { gen-interval level-1 } (interval-value) } | { {
     gen-interval level-2 } (interval-value) } | max-lifetime
     (lifetime-value) | refresh-interval (interval-value) }
    */
    container lsp {
      description
        "Set IS-IS LSP parameters";
      leaf gen-interval-level-1 {
        type uint8 {
          range "1..120";
        }
        default "10";
        description
          "Minimum interval between regenerating same LSP";
      }
      leaf gen-interval-level-2 {
        type uint8 {
          range "1..120";
        }
        default "10";
        description
          "Minimum interval between regenerating same LSP";
      }
      leaf max-lifetime {
        type uint16 {
          range "120..65535";
        }
        default "1200";
        description
          "Set maximum lifetime of locally generated LSPs";
      }
      leaf refresh-interval {
        type uint16 {
          range "30..65535";
        }
        default "900";
        description
          "Set LSP refresh interval";
      }
    }
    /*
    maximum { paths (paths-value) | redistribute (prefix-num) [
     retry-interval (delay-num) ] }
    */
    container maximum {
      description
        "Set maximum value of ISIS parameters";
      leaf paths {
        type uint8 {
          range "1..16";
        }
        default "8";
        description
          "Forward packets over multiple paths";
      }
      container redistribute {
        presence "";
        description
          "Set maximum number of prefix to be redistributed into
           ISIS";
        leaf prefix-num {
          type uint32 {
            range "1..1000000";
          }
          mandatory true;
          description
            "Number of prefixes";
        }
        leaf retry-interval {
          type uint16 {
            range "120..7200";
          }
          default "600";
          description
            "Retry in seconds to refresh the redistribution into
             ISIS";
        }
      }
    }
    /*
    metric-style { short | transition | wide } [ level-1 |
     level-2 ]
    */
    container metric-style {
      description
        "Define metric encoding styles advertised and used in
         computation";
      leaf metric-style-choice {
        type enumeration {
          enum short {
            value 0;
            description
              "Advertise and use for computation short (10589)
               style only";
          }
          enum transition {
            value 1;
            description
              "Advertise short and wide style";
          }
          enum wide {
            value 2;
            description
              "Advertise and use for computation wide (TE) style
               only (default)";
          }
        }
        default "wide";
        description
          "leaf metric-style-choice.";
      }
      leaf metric-style-opt1 {
        type enumeration {
          enum level-1 {
            value 0;
            description
              "Metric style for level-1 only";
          }
          enum level-2 {
            value 1;
            description
              "Metric style for level-2 only";
          }
        }
        description
          "leaf metric-style-opt1.";
      }
    }
    /*
    net (net-value)
    */
    leaf net {
      type string;
      status obsolete;
      description
        "Configure an area address and system ID";
    }
    /*
    graceful-restart [ (restart-time) ]
    */
    container graceful-restart {
      description
        "IS-IS restart with non-stop forwarding";
      leaf graceful-restart-enable {
        type boolean;
        default "true";
        description
          "Enable/Disable graceful-restart-enable";
      }
      leaf restart-time {
        when "../graceful-restart-enable='true'" {
          description
            "";
        }
        type uint16 {
          range "10..900";
        }
        default "120";
        description
          "Time in seconds after IS-IS restart";
      }
    }
    /*
    nonstop-routing
    */
    leaf nonstop-routing {
      if-feature nonstop-routing;
      type empty;
      description
        "IS-IS with nonstop routing";
    }
    /*
    set-overload-bit [ on-startup (start-time-value) | bgp-
     converge-delay  (time-value) | strict-bgp-tracking ]
    */
    container set-overload-bit {
      presence "";
      description
        "Signal other routers not to traverse this router in
         SPF";
      choice set-overload-bit-opt {
        case on-startup {
          leaf on-startup {
            type uint16 {
              range "10..3600";
            }
            default "210";
            description
              "Set overload-bit only temporarily at isis
               startup";
          }
        }
        case bgp-converge-delay {
          leaf bgp-converge-delay {
            type uint16 {
              range "10..3600";
            }
            default "210";
            description
              "Set overload-bit temporarily waiting for bgp
               convergence";
          }
        }
        case strict-bgp-tracking {
          leaf strict-bgp-tracking {
            type empty;
            description
              "Set overload-bit as long as bgp is not converged";
          }
        }
      }
    }
    /*
    snmp traps { all | { adjacencychange | areamismatch |
     attempttoexceedmaxsequence | authentication |
     authenticationtype | corruptedlspdetected | databaseoverload
     | idlenmismatch | lsperrordetected | lsptoolargetopropagate
     | manualaddressdrops | maxareaaddressmismatch |
     origlspbuffsizemismatch | ownlsppurge |
     protocolssupportedmismatch | rejectedadjacency |
     sequencenumberskip | versionskew } }
    */
    container snmp-traps {
      description
        "Configure SNMP traps";
      choice snmp-traps {
        case all {
          leaf all {
            type empty;
            description
              "Enable sending all supported ISIS traps";
          }
        }
        case snmp-traps-choice {
          leaf snmp-traps-choice {
            type bits {
              bit adjacencychange {
                position 0;
                description
                  "Enable sending isisAdjacencyChange traps";
              }
              bit areamismatch {
                position 1;
                description
                  "Enable sending isisAreaMismatch traps";
              }
              bit attempttoexceedmaxsequence {
                position 2;
                description
                  "Enable sending isisAttemptToExceedMaxSequence
                   traps";
              }
              bit authentication {
                position 3;
                description
                  "Enable sending isisAuthenticationFailure
                   traps";
              }
              bit authenticationtype {
                position 4;
                description
                  "Enable sending isisAuthenticationTypeFailure
                   traps";
              }
              bit corruptedlspdetected {
                position 5;
                description
                  "Enable sending isisCorruptedLSPDetected
                   traps";
              }
              bit databaseoverload {
                position 6;
                description
                  "Enable sending isisDatabaseOverload traps";
              }
              bit idlenmismatch {
                position 7;
                description
                  "Enable sending isisIdLenMismatch traps";
              }
              bit lsperrordetected {
                position 8;
                description
                  "Enable sending isisLSPErrorDetected traps";
              }
              bit lsptoolargetopropagate {
                position 9;
                description
                  "Enable sending isisLSPTooLargeToPropagate
                   traps";
              }
              bit manualaddressdrops {
                position 10;
                description
                  "Enable sending isisManualAddressDrops traps";
              }
              bit maxareaaddressmismatch {
                position 11;
                description
                  "Enable sending isisMaxAreaAddressMismatch
                   traps";
              }
              bit origlspbuffsizemismatch {
                position 12;
                description
                  "Enable sending isisOrigLSPBuffSizeMismatch
                   traps";
              }
              bit ownlsppurge {
                position 13;
                description
                  "Enable sending isisOwnLSPPurge traps";
              }
              bit protocolssupportedmismatch {
                position 14;
                description
                  "Enable sending isisProtocolsSupportedMismatch
                   traps";
              }
              bit rejectedadjacency {
                position 15;
                description
                  "Enable sending isisRejectedAdjacency traps";
              }
              bit sequencenumberskip {
                position 16;
                description
                  "Enable sending isisSeqNoSkip traps";
              }
              bit versionskew {
                position 17;
                description
                  "Enable sending isisVersionSkew traps";
              }
            }
            description
              "leaf snmp-traps-choice.";
          }
        }
      }
    }
    /*
    spf { { { holddown level-1 } (holddown-value) } |  { {
     holddown level-2 } (holddown-value) } | { { interval level-1
     } (interval-value) } | { { interval level-2 } (interval-
     value) } }
    */
    container spf {
      description
        "Set IS-IS SPF parameters";
      leaf holddown-level-1 {
        type uint16 {
          range "1..65535";
        }
        default "5";
        description
          "Interval to delay SPF after receiving the first
           update";
      }
      leaf holddown-level-2 {
        type uint16 {
          range "1..65535";
        }
        default "5";
        description
          "Interval to delay SPF after receiving the first
           update";
      }
      leaf interval-level-1 {
        type uint8 {
          range "1..120";
        }
        default "10";
        description
          "Minimum interval between SPF calculations";
      }
      leaf interval-level-2 {
        type uint8 {
          range "1..120";
        }
        default "10";
        description
          "Minimum interval between SPF calculations";
      }
    }
    /*
    lfa-spf { scheduling (number-limit) | holddown (holddown-
     value) }
    */
    container lfa-spf {
      description
        "Configure Loop Free Alternative(LFA) SPF parameters";
      leaf scheduling {
        type uint8 {
          range "1..64";
        }
        default "8";
        description
          "Configure LFA-SPF scheduling parameters";
      }
      leaf holddown {
        type uint16 {
          range "500..3000";
        }
        default "1000";
        description
          "Configure LFA SPF holddown value";
      }
    }
    /*
    fast-convergence [ (fastconv-msdelay) (fastconv-extraspfs) ]
    */
    container fast-convergence {
      description
        "Configure fast convergence scheduling parameters";
      leaf fast-convergence-enable {
        type boolean;
        default "true";
        description
          "Enable/Disable fast-convergence-enable";
      }
      container fast-convergence-opt {
        description
          "container fast-convergence-opt.";
        leaf fastconv-msdelay {
          type uint16 {
            range "0..999";
          }
          default "100";
          description
            "SPF delay value (in milli-seconds)";
        }
        leaf fastconv-extraspfs {
          type uint8 {
            range "0..15";
          }
          default "3";
          description
            "Number of additional SPFs allowed in hold-time";
        }
      }
    }
    /*
    traffic-engineering { level-1 | level-2 | level-1-2 }
    */
    leaf traffic-engineering {
      type enumeration {
        enum level-1 {
          value 0;
          description
            "mpls TE for level-1 only";
        }
        enum level-2 {
          value 1;
          description
            "mpls TE for level-2 only";
        }
        enum level-1-2 {
          value 2;
          description
            "mpls TE for level-1-2";
        }
      }
      description
        "Set mpls traffic-engineering levels";
    }
    /*
    ldp-igp-synchronization [ timeout (holddown-value) ]
    */
    container ldp-igp-synchronization {
      presence "";
      description
        "set ldp-igp synchronization";
      leaf timeout {
        type uint16 {
          range "5..65535";
        }
        description
          "ldp isis sync expire time";
      }
    }
    /*
    address-family { ipv4 { unicast | multicast } | ipv6 {
     unicast | multicast } | ipv4-conf { unicast | multicast } }
    */
    container address-family {
      description
        "Enable IS-IS for an address-family/topology";
      container ipv4 {
        status obsolete;
        description
          "Enable IS-IS for IPv4";
        container unicast {
          description
            "Enable IS-IS for IPv4 unicast topology";
          leaf unicast-enable {
            type boolean;
            default "true";
            description
              "Enable/Disable unicast-enable";
          }
          uses isis-af-ipv4-grp;
        }
        leaf multicast {
          if-feature af_ipv4_multicast;
          type empty;
          description
            "Enable IS-IS for IPv4 multicast topology";
        }
      }
      container ipv6 {
        description
          "Enable IS-IS for IPv6";
        container unicast {
          presence "";
          description
            "Enable IS-IS for IPv6 unicast topology";
          uses isis-af-ipv6-grp;
        }
        leaf multicast {
          if-feature af_ipv6_multicast;
          type empty;
          description
            "Enable IS-IS for IPv6 multicast topology";
        }
      }
      container ipv4-conf {
        description
          "Enable IS-IS for IPv4";
        container unicast {
          presence "";
          description
            "Enable IS-IS for IPv4 unicast topology";
          leaf unicast-enable {
            type boolean;
            default "true";
            description
              "Enable/Disable unicast-enable";
          }
          uses isis-af-ipv4-grp;
        }
        leaf multicast {
          if-feature af_ipv4_multicast;
          type empty;
          description
            "Enable IS-IS for IPv4 multicast topology";
        }
      }
    }
    /*
    interface (intf-name)
    */
    list interface {
      key "interface";
      description
        "Enable IS-IS routing on interface";
      leaf interface {
        type leafref {
          path "/if:interfaces/if:interface/if:name";
        }
        description
          "Interface name";
      }
      uses isis-if-grp;
    }
    /*
    net_n (net-value-n)
    */
    list net_n {
      key "net_n";
      description
        "Configure an area address and system ID";
      leaf net_n {
        type string;
        description
          "XX.XXXX.  ... .XXXX.XX  Network Entity Title(NET).
           For example: 47.0001.1111.2222.3333.00   where
           1111.2222.3333 is the systemID";
      }
    }
    /*
    segment-routing
    */
    container segment-routing {
      description
        "Configure segment routing";
      list global-block {
        key "global-min";
        description
          "Configure segment routing";
        leaf global-min {
          type uint32 {
            range "16000..262143|999424..1015807";
          }
          description
            "start of SRGB range \"16000.. 262143 |
             999424..1015807\"";
        }
        leaf through {
          type uint32 {
            range "16000..262143|999424..1015807";
          }
          mandatory true;
          description
            "keyword";
        }
      }
    }
  }

  grouping isis-af-ipv4-grp {
    description
      "ISIS address family ipv4 configuration mode";
    /*
    microloop-delay (delay-val)
    */
    leaf microloop-delay {
      type uint16 {
        range "10..15000";
      }
      description
        "Configure micro-loop avoidance delay timer in msec";
    }
    /*
    segment-routing
    */
    container segment-routing {
      description
        "Configure segment routing";
      list prefix-sid-map-group {
        key "group-string";
        description
          "Configure SR Mapping Server prefix-sid group";
        leaf group-string {
          type string;
          description
            "Prefix sid group name,enter the # or the ! to be
             prefixed with backslash \\.";
        }
        leaf prefix-sid-map-group-choice {
          type enumeration {
            enum level-1 {
              value 0;
              description
                "Advertise prefix-sid mappings to level-1";
            }
            enum level-2 {
              value 1;
              description
                "Advertise prefix-sid mappings to level-2";
            }
          }
          mandatory true;
          description
            "leaf prefix-sid-map-group-choice.";
        }
      }
      container distance {
        presence "";
        description
          "Configure admin distance for SR LSPs";
        leaf sr-value {
          type uint8 {
            range "1..255";
          }
          default "14";
          description
            "SR admin distance value";
        }
      }
      list global-block {
        key "global-min";
        description
          "Configure segment routing";
        leaf global-min {
          type uint32 {
            range "16000..262143|999424..1015807";
          }
          description
            "start of SRGB range \"16000.. 262143 |
             999424..1015807\"";
        }
        leaf through {
          type uint32 {
            range "16000..262143|999424..1015807";
          }
          mandatory true;
          description
            "keyword";
        }
      }
    }
    /*
    prefix-hiding
    */
    leaf prefix-hiding {
      type empty;
      description
        "Prefix hiding for this address-family";
    }
    /*
    redistribute { bgf | bgp { (redistribute-bgpas) | (bgpas-
     aann) } | cg-nat | application sgsn-mme | connected | epg |
     ipsec | isis (opt-tag) | lim | msp | nat | rip (opt-tag) |
     sasn | seg | static [dvsr] | subscriber [address | static ]
     | vrrp | wifi-ac | wmg } { level-1 | level-2 } [ metric
     (metric-num) ] [ metric-type { external | internal } ] [
     route-map (routemap-str) ]
    */
    container redistribute {
      description
        "Redistribute information from another routing protocol";
      list bgf {
        if-feature af_redis_bgf;
        key "bgf-choice";
        max-elements 2;
        description
          "Border Gateway Function (BGF) routes";
        leaf bgf-choice {
          type enumeration {
            enum level-1 {
              value 0;
              description
                "Redistribute into level-1";
            }
            enum level-2 {
              value 1;
              description
                "Redistribute into level-2";
            }
          }
          description
            "leaf bgf-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list bgp {
        key "bgp bgp-choice";
        description
          "Border Gateway Protocol (BGP)";
        leaf bgp {
          type union {
            type uint32 {
              range "1..4294967295";
            }
            type string;
          }
          description
            "leaf bgp.";
        }
        leaf bgp-choice {
          type enumeration {
            enum level-1 {
              value 0;
              description
                "Redistribute into level-1";
            }
            enum level-2 {
              value 1;
              description
                "Redistribute into level-2";
            }
          }
          description
            "leaf bgp-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list cg-nat {
        if-feature af_redis_cgnat;
        key "cg-nat-choice";
        max-elements 2;
        description
          "Carrier Grade Network Address Translation (CGNAT)
           routes";
        leaf cg-nat-choice {
          type enumeration {
            enum level-1 {
              value 0;
              description
                "Redistribute into level-1";
            }
            enum level-2 {
              value 1;
              description
                "Redistribute into level-2";
            }
          }
          description
            "leaf cg-nat-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list application-sgsn-mme {
        if-feature af_redis_app;
        key "application-sgsn-mme-choice";
        description
          "SGSN and Mobility Management Entity(MME) routes";
        leaf application-sgsn-mme-choice {
          type enumeration {
            enum level-1 {
              value 0;
              description
                "Redistribute into level-1";
            }
            enum level-2 {
              value 1;
              description
                "Redistribute into level-2";
            }
          }
          description
            "leaf application-sgsn-mme-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list connected {
        key "connected-choice";
        description
          "Directly connected routes";
        leaf connected-choice {
          type enumeration {
            enum level-1 {
              value 0;
              description
                "Redistribute into level-1";
            }
            enum level-2 {
              value 1;
              description
                "Redistribute into level-2";
            }
          }
          description
            "leaf connected-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list epg {
        if-feature af_redis_epg;
        key "epg-choice";
        description
          "Evolved Packet Gateway (EPG) routes";
        leaf epg-choice {
          type enumeration {
            enum level-1 {
              value 0;
              description
                "Redistribute into level-1";
            }
            enum level-2 {
              value 1;
              description
                "Redistribute into level-2";
            }
          }
          description
            "leaf epg-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list ipsec {
        if-feature af_redis_ipsec;
        key "ipsec-choice";
        description
          "IPsec routes";
        leaf ipsec-choice {
          type enumeration {
            enum level-1 {
              value 0;
              description
                "Redistribute into level-1";
            }
            enum level-2 {
              value 1;
              description
                "Redistribute into level-2";
            }
          }
          description
            "leaf ipsec-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list isis {
        key "isis isis-choice";
        description
          "ISO IS-IS";
        leaf isis {
          type string;
          description
            "ISO routing area tag";
        }
        leaf isis-choice {
          type enumeration {
            enum level-1 {
              value 0;
              description
                "Redistribute into level-1";
            }
            enum level-2 {
              value 1;
              description
                "Redistribute into level-2";
            }
          }
          description
            "leaf isis-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list lim {
        if-feature af_redis_seg;
        key "lim-choice";
        description
          "Lawful Interception Module(LIM) routes";
        leaf lim-choice {
          type enumeration {
            enum level-1 {
              value 0;
              description
                "Redistribute into level-1";
            }
            enum level-2 {
              value 1;
              description
                "Redistribute into level-2";
            }
          }
          description
            "leaf lim-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list msp {
        if-feature af_redis_msp;
        key "msp-choice";
        description
          "Multi-Service Proxy (MSP) routes";
        leaf msp-choice {
          type enumeration {
            enum level-1 {
              value 0;
              description
                "Redistribute into level-1";
            }
            enum level-2 {
              value 1;
              description
                "Redistribute into level-2";
            }
          }
          description
            "leaf msp-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list nat {
        if-feature af_redis_nat;
        key "nat-choice";
        description
          "Network Address Translation (NAT)";
        leaf nat-choice {
          type enumeration {
            enum level-1 {
              value 0;
              description
                "Redistribute into level-1";
            }
            enum level-2 {
              value 1;
              description
                "Redistribute into level-2";
            }
          }
          description
            "leaf nat-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list rip {
        if-feature af_ipv4_redis_rip;
        key "rip rip-choice";
        description
          "RIP protocol";
        leaf rip {
          type string;
          description
            "RIP protocol instance name";
        }
        leaf rip-choice {
          type enumeration {
            enum level-1 {
              value 0;
              description
                "Redistribute into level-1";
            }
            enum level-2 {
              value 1;
              description
                "Redistribute into level-2";
            }
          }
          description
            "leaf rip-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list sasn {
        if-feature af_redis_sasn;
        key "sasn-choice";
        description
          "Service-Aware Support Node (SASN) routes";
        leaf sasn-choice {
          type enumeration {
            enum level-1 {
              value 0;
              description
                "Redistribute into level-1";
            }
            enum level-2 {
              value 1;
              description
                "Redistribute into level-2";
            }
          }
          description
            "leaf sasn-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list seg {
        if-feature af_redis_seg;
        key "seg-choice";
        description
          "Security Gateway (SEG) routes";
        leaf seg-choice {
          type enumeration {
            enum level-1 {
              value 0;
              description
                "Redistribute into level-1";
            }
            enum level-2 {
              value 1;
              description
                "Redistribute into level-2";
            }
          }
          description
            "leaf seg-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list static {
        key "static-choice";
        description
          "Static routes";
        leaf static-choice {
          type enumeration {
            enum level-1 {
              value 0;
              description
                "Redistribute into level-1";
            }
            enum level-2 {
              value 1;
              description
                "Redistribute into level-2";
            }
          }
          description
            "leaf static-choice.";
        }
        leaf dvsr {
          type empty;
          description
            "DVSR (dynamically verified static routing)";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list subscriber {
        if-feature af_ipv4_redis_subscriber;
        key "subscriber-choice1";
        description
          "Subscriber routes";
        leaf subscriber-choice1 {
          type enumeration {
            enum level-1 {
              value 0;
              description
                "Redistribute into level-1";
            }
            enum level-2 {
              value 1;
              description
                "Redistribute into level-2";
            }
          }
          description
            "leaf subscriber-choice1.";
        }
        leaf subscriber-opt {
          type enumeration {
            enum address {
              value 0;
              description
                "Subscriber address routes";
            }
            enum static {
              value 1;
              description
                "Subscriber static routes";
            }
          }
          description
            "leaf subscriber-opt.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list vrrp {
        if-feature af_redis_vrrp;
        key "vrrp-choice";
        description
          "Virtual Router Redundancy (VRRP) routes";
        leaf vrrp-choice {
          type enumeration {
            enum level-1 {
              value 0;
              description
                "Redistribute into level-1";
            }
            enum level-2 {
              value 1;
              description
                "Redistribute into level-2";
            }
          }
          description
            "leaf vrrp-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list wifi-ac {
        if-feature af_redis_wifiac;
        key "wifi-ac-choice";
        description
          "WiFi Access Concentrator (WiFiAC) routes";
        leaf wifi-ac-choice {
          type enumeration {
            enum level-1 {
              value 0;
              description
                "Redistribute into level-1";
            }
            enum level-2 {
              value 1;
              description
                "Redistribute into level-2";
            }
          }
          description
            "leaf wifi-ac-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list wmg {
        if-feature af_redis_wmg;
        key "wmg-choice";
        description
          "Wi-Fi Mobility Gateway (WMG) routes";
        leaf wmg-choice {
          type enumeration {
            enum level-1 {
              value 0;
              description
                "Redistribute into level-1";
            }
            enum level-2 {
              value 1;
              description
                "Redistribute into level-2";
            }
          }
          description
            "leaf wmg-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list ospf {
        key "ospf ospf-choice1";
        description
          "Open Shortest Path First (OSPF)";
        leaf ospf {
          type uint16 {
            range "1..65535";
          }
          description
            "OSPF instance";
        }
        leaf ospf-choice1 {
          type enumeration {
            enum level-1 {
              value 0;
              description
                "Redistribute into level-1";
            }
            enum level-2 {
              value 1;
              description
                "Redistribute into level-2";
            }
          }
          description
            "leaf ospf-choice1.";
        }
        choice ospf-opt {
          case match {
            container match {
              presence "";
              description
                "Match a specific OSPF route type";
              leaf intra-area {
                type empty;
                description
                  "Redistribute OSPF Intra-area routes";
              }
              leaf inter-area {
                type empty;
                description
                  "Redistribute OSPF Inter-area routes";
              }
              container external {
                presence "";
                description
                  "Redistribute OSPF external routes";
                leaf external-opt {
                  type enumeration {
                    enum type-1 {
                      value 0;
                      description
                        "Redistribute OSPF External routes (Type
                         1)";
                    }
                    enum type-2 {
                      value 1;
                      description
                        "Redistribute OSPF External routes (Type
                         2)";
                    }
                  }
                  description
                    "leaf external-opt.";
                }
              }
              container nssa {
                presence "";
                description
                  "Redistribute OSPF NSSA routes";
                leaf nssa-opt {
                  type enumeration {
                    enum type-1 {
                      value 0;
                      description
                        "Redistribute OSPF NSSA type 1 routes";
                    }
                    enum type-2 {
                      value 1;
                      description
                        "Redistribute OSPF NSSA type 2 routes";
                    }
                  }
                  description
                    "leaf nssa-opt.";
                }
              }
            }
          }
          case metric {
            leaf metric {
              type uint32 {
                range "0..16777214";
              }
              default "0";
              description
                "Metric for redistributed routes";
            }
          }
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
    }
    /*
    interarea-distribute { l1-to-l2 | l2-to-l1 } [ prefix-list
     (list-value) ]
    */
    list interarea-distribute {
      key "interarea-distribute-choice";
      description
        "Interarea IP route leaking";
      leaf interarea-distribute-choice {
        type enumeration {
          enum l1-to-l2 {
            value 0;
            description
              "IP route leaking from level-1 into level-2";
          }
          enum l2-to-l1 {
            value 1;
            description
              "IP route leaking from level-2 into level-1";
          }
        }
        description
          "leaf interarea-distribute-choice.";
      }
      leaf prefix-list {
        type string;
        description
          "Filter redistributed routes";
      }
    }
    /*
    summary-address { addr-ipv4 (address-prefix) [ level-1 |
     level-2 ] [ tag (tag-val) ] }
    */
    container summary-address {
      description
        "Configure IP address summaries";
      list addr-ipv4 {
        key "address-prefix";
        description
          "False token for ipv4 list";
        leaf address-prefix {
          type typesrouter6000:ipos-ip-prefix;
          description
            "IP summary address prefix";
        }
        leaf addr-ipv4-opt {
          type enumeration {
            enum level-1 {
              value 0;
              description
                "IP summary for level-1 only";
            }
            enum level-2 {
              value 1;
              description
                "IP summary for level-2 only";
            }
          }
          description
            "leaf addr-ipv4-opt.";
        }
        leaf tag {
          type uint32 {
            range "1..4294967295";
          }
          description
            "configure route tag";
        }
      }
    }
    /*
    priority-prefix (prefix-list)
    */
    leaf priority-prefix {
      type string;
      description
        "Configure prioritization of selected prefixes";
    }
    /*
    link-state id (id-num)
    */
    container link-state {
      description
        "Configure IGP LS";
      leaf id {
        type uint64 {
          range "0..18446744073709551615";
        }
        description
          "IGP-LS ID";
      }
    }
  }

  grouping isis-af-ipv6-grp {
    description
      "ISIS address family ipv6 configuration mode";
    /*
    prefix-hiding
    */
    leaf prefix-hiding {
      type empty;
      description
        "Prefix hiding for this address-family";
    }
    /*
    redistribute { bgf | bgp { (redistribute-bgpas) | (bgpas-
     aann) } | cg-nat | application sgsn-mme | connected | epg |
     isis (opt-tag) | lim | msp | nat | ripng (ripng-tag) | sasn
     | seg | static [dvsr] | subscriber-v6 { address | dhcp-pd |
     nd | static } | wifi-ac | wmg } { level-1 | level-2 } [
     metric (metric-num) ] [ metric-type { external | internal }
     ] [ route-map (routemap-str) ]
    */
    container redistribute {
      description
        "Redistribute information from another routing protocol";
      list bgf {
        if-feature af_redis_bgf;
        key "bgf-choice";
        max-elements 2;
        description
          "Border Gateway Function (BGF) routes";
        leaf bgf-choice {
          type enumeration {
            enum level-1 {
              value 0;
              description
                "Redistribute into level-1";
            }
            enum level-2 {
              value 1;
              description
                "Redistribute into level-2";
            }
          }
          description
            "leaf bgf-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list bgp {
        key "bgp bgp-choice";
        description
          "Border Gateway Protocol (BGP)";
        leaf bgp {
          type union {
            type uint32 {
              range "1..4294967295";
            }
            type string;
          }
          description
            "leaf bgp.";
        }
        leaf bgp-choice {
          type enumeration {
            enum level-1 {
              value 0;
              description
                "Redistribute into level-1";
            }
            enum level-2 {
              value 1;
              description
                "Redistribute into level-2";
            }
          }
          description
            "leaf bgp-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list cg-nat {
        if-feature af_redis_cgnat;
        key "cg-nat-choice";
        max-elements 2;
        description
          "Carrier Grade Network Address Translation (CGNAT)
           routes";
        leaf cg-nat-choice {
          type enumeration {
            enum level-1 {
              value 0;
              description
                "Redistribute into level-1";
            }
            enum level-2 {
              value 1;
              description
                "Redistribute into level-2";
            }
          }
          description
            "leaf cg-nat-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list application-sgsn-mme {
        if-feature af_redis_app;
        key "application-sgsn-mme-choice";
        description
          "SGSN and Mobility Management Entity(MME) routes";
        leaf application-sgsn-mme-choice {
          type enumeration {
            enum level-1 {
              value 0;
              description
                "Redistribute into level-1";
            }
            enum level-2 {
              value 1;
              description
                "Redistribute into level-2";
            }
          }
          description
            "leaf application-sgsn-mme-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list connected {
        key "connected-choice";
        description
          "Directly connected routes";
        leaf connected-choice {
          type enumeration {
            enum level-1 {
              value 0;
              description
                "Redistribute into level-1";
            }
            enum level-2 {
              value 1;
              description
                "Redistribute into level-2";
            }
          }
          description
            "leaf connected-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list epg {
        if-feature af_redis_epg;
        key "epg-choice";
        description
          "Evolved Packet Gateway (EPG) routes";
        leaf epg-choice {
          type enumeration {
            enum level-1 {
              value 0;
              description
                "Redistribute into level-1";
            }
            enum level-2 {
              value 1;
              description
                "Redistribute into level-2";
            }
          }
          description
            "leaf epg-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list isis {
        key "isis isis-choice";
        description
          "ISO IS-IS";
        leaf isis {
          type string;
          description
            "ISO routing area tag";
        }
        leaf isis-choice {
          type enumeration {
            enum level-1 {
              value 0;
              description
                "Redistribute into level-1";
            }
            enum level-2 {
              value 1;
              description
                "Redistribute into level-2";
            }
          }
          description
            "leaf isis-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list lim {
        if-feature af_redis_seg;
        key "lim-choice";
        description
          "Lawful Interception Module(LIM) routes";
        leaf lim-choice {
          type enumeration {
            enum level-1 {
              value 0;
              description
                "Redistribute into level-1";
            }
            enum level-2 {
              value 1;
              description
                "Redistribute into level-2";
            }
          }
          description
            "leaf lim-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list msp {
        if-feature af_redis_msp;
        key "msp-choice";
        description
          "Multi-Service Proxy (MSP) routes";
        leaf msp-choice {
          type enumeration {
            enum level-1 {
              value 0;
              description
                "Redistribute into level-1";
            }
            enum level-2 {
              value 1;
              description
                "Redistribute into level-2";
            }
          }
          description
            "leaf msp-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list nat {
        if-feature af_redis_nat;
        key "nat-choice";
        description
          "Network Address Translation (NAT)";
        leaf nat-choice {
          type enumeration {
            enum level-1 {
              value 0;
              description
                "Redistribute into level-1";
            }
            enum level-2 {
              value 1;
              description
                "Redistribute into level-2";
            }
          }
          description
            "leaf nat-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list ripng {
        if-feature af_ipv6_redis_rip;
        key "ripng ripng-choice";
        description
          "RIP protocol";
        leaf ripng {
          type string;
          description
            "RIP protocol instance name";
        }
        leaf ripng-choice {
          type enumeration {
            enum level-1 {
              value 0;
              description
                "Redistribute into level-1";
            }
            enum level-2 {
              value 1;
              description
                "Redistribute into level-2";
            }
          }
          description
            "leaf ripng-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list sasn {
        if-feature af_redis_sasn;
        key "sasn-choice";
        description
          "Service-Aware Support Node (SASN) routes";
        leaf sasn-choice {
          type enumeration {
            enum level-1 {
              value 0;
              description
                "Redistribute into level-1";
            }
            enum level-2 {
              value 1;
              description
                "Redistribute into level-2";
            }
          }
          description
            "leaf sasn-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list seg {
        if-feature af_redis_seg;
        key "seg-choice";
        description
          "Security Gateway (SEG) routes";
        leaf seg-choice {
          type enumeration {
            enum level-1 {
              value 0;
              description
                "Redistribute into level-1";
            }
            enum level-2 {
              value 1;
              description
                "Redistribute into level-2";
            }
          }
          description
            "leaf seg-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list static {
        key "static-choice";
        description
          "Static routes";
        leaf static-choice {
          type enumeration {
            enum level-1 {
              value 0;
              description
                "Redistribute into level-1";
            }
            enum level-2 {
              value 1;
              description
                "Redistribute into level-2";
            }
          }
          description
            "leaf static-choice.";
        }
        leaf dvsr {
          type empty;
          description
            "DVSR (dynamically verified static routing)";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list subscriber-v6 {
        if-feature af_ipv6_redis_subscriber;
        key "subscriber-v6 subscriber-v6-choice";
        description
          "Subscriber routes";
        leaf subscriber-v6 {
          type enumeration {
            enum address {
              value 0;
              description
                "Subscriber address routes";
            }
            enum dhcp-pd {
              value 1;
              description
                "Subscriber static routes";
            }
            enum nd {
              value 2;
              description
                "Subscriber DHCP Prefix Delegation (dhcp-pd)
                 routes";
            }
            enum static {
              value 3;
              description
                "Subscriber Neighbor Discovery (ND) routes";
            }
          }
          description
            "leaf subscriber-v6.";
        }
        leaf subscriber-v6-choice {
          type enumeration {
            enum level-1 {
              value 0;
              description
                "Redistribute into level-1";
            }
            enum level-2 {
              value 1;
              description
                "Redistribute into level-2";
            }
          }
          description
            "leaf subscriber-v6-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list wifi-ac {
        if-feature af_redis_wifiac;
        key "wifi-ac-choice";
        description
          "WiFi Access Concentrator (WiFiAC) routes";
        leaf wifi-ac-choice {
          type enumeration {
            enum level-1 {
              value 0;
              description
                "Redistribute into level-1";
            }
            enum level-2 {
              value 1;
              description
                "Redistribute into level-2";
            }
          }
          description
            "leaf wifi-ac-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list wmg {
        if-feature af_redis_wmg;
        key "wmg-choice";
        description
          "Wi-Fi Mobility Gateway (WMG) routes";
        leaf wmg-choice {
          type enumeration {
            enum level-1 {
              value 0;
              description
                "Redistribute into level-1";
            }
            enum level-2 {
              value 1;
              description
                "Redistribute into level-2";
            }
          }
          description
            "leaf wmg-choice.";
        }
        leaf metric {
          type uint32 {
            range "0..16777214";
          }
          default "0";
          description
            "Metric for redistributed routes";
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
      list ospf3 {
        key "ospf3 ospf3-choice1";
        description
          "Open Shortest Path First Ver3 (OSPF3)";
        leaf ospf3 {
          type uint16 {
            range "1..65535";
          }
          description
            "OSPF3 instance";
        }
        leaf ospf3-choice1 {
          type enumeration {
            enum level-1 {
              value 0;
              description
                "Redistribute into level-1";
            }
            enum level-2 {
              value 1;
              description
                "Redistribute into level-2";
            }
          }
          description
            "leaf ospf3-choice1.";
        }
        choice ospf3-opt {
          case match {
            container match {
              presence "";
              description
                "Match a specific OSPF3 route type";
              leaf intra-area {
                type empty;
                description
                  "Redistribute OSPFv3 Intra-area routes";
              }
              leaf inter-area {
                type empty;
                description
                  "Redistribute OSPFv3 Inter-area routes";
              }
              container external {
                presence "";
                description
                  "Redistribute OSPFv3 external routes";
                leaf external-opt {
                  type enumeration {
                    enum type-1 {
                      value 0;
                      description
                        "Redistribute OSPFv3 External routes
                         (Type 1)";
                    }
                    enum type-2 {
                      value 1;
                      description
                        "Redistribute OSPFv3 External routes
                         (Type 2)";
                    }
                  }
                  description
                    "leaf external-opt.";
                }
              }
              container nssa {
                presence "";
                description
                  "Redistribute OSPFv3 NSSA routes";
                leaf nssa-opt {
                  type enumeration {
                    enum type-1 {
                      value 0;
                      description
                        "Redistribute OSPFv3 NSSA type 1 routes";
                    }
                    enum type-2 {
                      value 1;
                      description
                        "Redistribute OSPFv3 NSSA type 2 routes";
                    }
                  }
                  description
                    "leaf nssa-opt.";
                }
              }
            }
          }
          case metric {
            leaf metric {
              type uint32 {
                range "0..16777214";
              }
              default "0";
              description
                "Metric for redistributed routes";
            }
          }
        }
        leaf metric-type {
          type enumeration {
            enum external {
              value 0;
              description
                "External metric type";
            }
            enum internal {
              value 1;
              description
                "Internal metric type";
            }
          }
          description
            "Metric type for redistributed routes";
        }
        leaf route-map {
          type string;
          description
            "Route map reference";
        }
      }
    }
    /*
    interarea-distribute { l1-to-l2 | l2-to-l1 } [  ipv6-prefix-
     list (list-value) ]
    */
    list interarea-distribute {
      key "interarea-distribute-choice";
      description
        "Interarea IP route leaking";
      leaf interarea-distribute-choice {
        type enumeration {
          enum l1-to-l2 {
            value 0;
            description
              "IP route leaking from level-1 into level-2";
          }
          enum l2-to-l1 {
            value 1;
            description
              "IP route leaking from level-2 into level-1";
          }
        }
        description
          "leaf interarea-distribute-choice.";
      }
      leaf ipv6-prefix-list {
        type string;
        description
          "Filter redistributed ipv6 routes";
      }
    }
    /*
    summary-address { addr-ipv6 (address-prefix) [ level-1 |
     level-2 ] [ tag (tag-val) ] | addr-ipv6-conf (address-
     prefix) [ level-1 | level-2 ] [ tag (tag-val) ] }
    */
    container summary-address {
      description
        "Configure IP address summaries";
      list addr-ipv6 {
        key "address-prefix";
        status obsolete;
        description
          "False token for ipv6 list";
        leaf address-prefix {
          type inet:ipv6-prefix;
          description
            "IPv6 summary address prefix";
        }
        leaf addr-ipv6-opt {
          type enumeration {
            enum level-1 {
              value 0;
              description
                "IPv6 summary for level-1 only";
            }
            enum level-2 {
              value 1;
              description
                "IPv6 summary for level-2 only";
            }
          }
          description
            "leaf addr-ipv6-opt.";
        }
        leaf tag {
          type uint32 {
            range "1..4294967295";
          }
          description
            "configure route tag";
        }
      }
      list addr-ipv6-conf {
        key "address-prefix";
        description
          "False token for ipv6 list";
        leaf address-prefix {
          type typesrouter6000:ipv6-address-mask;
          description
            "IPv6 summary address prefix";
        }
        leaf addr-ipv6-conf-opt {
          type enumeration {
            enum level-1 {
              value 0;
              description
                "IPv6 summary for level-1 only";
            }
            enum level-2 {
              value 1;
              description
                "IPv6 summary for level-2 only";
            }
          }
          description
            "leaf addr-ipv6-conf-opt.";
        }
        leaf tag {
          type uint32 {
            range "1..4294967295";
          }
          description
            "configure route tag";
        }
      }
    }
    /*
    priority-prefix (prefix-list)
    */
    leaf priority-prefix {
      type string;
      description
        "Configure prioritization of selected prefixes";
    }
    /*
    microloop-delay (delay-val)
    */
    leaf microloop-delay {
      type uint16 {
        range "10..15000";
      }
      description
        "Configure micro-loop avoidance delay timer in msec";
    }
    /*
    segment-routing
    */
    container segment-routing {
      description
        "Configure segment routing";
      container srv6 {
        presence "";
        description
          "Configure segment routing srv6";
        uses srv6-grp;
      }
      container distance {
        presence "";
        description
          "Configure admin distance for SR LSPs";
        leaf sr-value {
          type uint8 {
            range "1..255";
          }
          default "14";
          description
            "SR admin distance value";
        }
      }
    }
    /*
    multi-topology [transition-send | transition-exclude-mt-
     tlvs]
    */
    container multi-topology {
      description
        "multi-topology mode";
      choice multi-topology-opt {
        case transition-send {
          leaf transition-send {
            type empty;
            description
              "multi-topology transition mode";
          }
        }
        case transition-exclude-mt-tlvs {
          leaf transition-exclude-mt-tlvs {
            type empty;
            description
              "Exclude MT TLVs from LSP";
          }
        }
      }
    }
  }

  grouping srv6-grp {
    description
      "AF SRV6 sub mode";
    /*
    locator (locid) [ level (levelval) ]
    */
    list locator {
      key "locid";
      description
        "Locator";
      leaf locid {
        type string;
        description
          "Locator ID";
      }
      leaf level {
        type string;
        description
          "Level";
      }
    }
  }

  grouping isis-if-af-grp {
    description
      "ISIS interface address family configuration mode";
    /*
    prefix-hiding [ ignore-global ]
    */
    container prefix-hiding {
      description
        "Hide interface prefix for this interface";
      leaf prefix-hiding-enable {
        type boolean;
        default "true";
        description
          "Enable/Disable prefix-hiding-enable";
      }
      leaf ignore-global {
        when "../prefix-hiding-enable='true'" {
          description
            "";
        }
        type empty;
        description
          "Ignore config at instance (address-family) level";
      }
    }
    /*
    prefix-sid index (global-value) [ node ] [ explicit-null |
     php ]
    */
    container prefix-sid-index {
      when "local-name(..) = 'unicast' and local-name(../..) ="
      + " 'ipv4-conf' and not(../../../../../../../ctxr6k:vpn-conf)" {
        description
          "prefix-sid option just exist under address-family
           ipv4 unicast.";
      }
      presence "";
      status obsolete;
      description
        "Index into the SRGB range";
      leaf global-value {
        type uint16 {
          range "0..16383";
        }
        mandatory true;
        description
          "Segment identifier";
      }
      leaf node {
        type empty;
        description
          "Configure as a node-segment identifier";
      }
      leaf prefix-sid-index-opt {
        type enumeration {
          enum explicit-null {
            value 0;
            description
              "Enable explicit-NULL operation";
          }
          enum php {
            value 1;
            description
              "Enable penultimate-hop pop operation";
          }
        }
        description
          "leaf prefix-sid-index-opt.";
      }
    }
    /*
    adjacency-sid absolute (local-value)
    */
    container adjacency-sid {
      when "local-name(..) = 'unicast' and not(../../../../../../.."
      + "/ctxr6k:vpn-conf)" {
        description
          "adjacency-sid option exists both under address-family
           ipv4 unicast and address-family ipv6 unicast.";
      }
      description
        "Configure adjacency-segment identifier for the
         interface";
      leaf absolute {
        type uint32 {
          range "983040..999423";
        }
        description
          "Identifier from local range";
      }
    }
    /*
    bfd
    */
    leaf bfd {
      type boolean;
      default "true";
      description
        "Enable/Disable bfd";
    }
    /*
    metric { level-1 (metric-value) | level-2 (metric-value) }
    */
    container metric {
      when "not(../../../../passive-interface)" {
        description
          "Configure a metric for non-passive interface only";
      }
      description
        "Configure a metric for non-passive interface only";
      leaf level-1 {
        type uint32 {
          range "1..16777215";
        }
        default "10";
        description
          "Configure metric value for level-1 only";
      }
      leaf level-2 {
        type uint32 {
          range "1..16777215";
        }
        default "10";
        description
          "Configure metric value for level-2 only";
      }
    }
    /*
    lfa [ backup | [ protect { link-only | node-only } ] [
     prefer ecmp | exclude ecmp ] [ remote-lfa ] ]
    */
    container lfa {
      when "local-name(..) = 'unicast'" {
        description
          "lfa just exist under address-family ipv4/ipv6
           unicast.";
      }
      presence "";
      description
        "Configure Loop Free Alternative (LFA) computation";
      leaf backup {
        type boolean;
        default "true";
        description
          "Enable/Disable backup";
      }
      container protect {
        description
          "container protect.";
        leaf protect {
          type enumeration {
            enum link-only {
              value 0;
              description
                "Only link protecting neighbors will be chosen
                 as LFAs";
            }
            enum node-only {
              value 1;
              description
                "Only node protecting neighbors will be chosen
                 as LFAs";
            }
          }
          description
            "Configure LFA protection constraints";
        }
        choice protect-opt {
          case prefer-ecmp {
            leaf prefer-ecmp {
              type empty;
              description
                "LFA selection prefers equal-cost multipath
                 nexthops";
            }
          }
          case exclude-ecmp {
            leaf exclude-ecmp {
              type empty;
              description
                "LFA selection excludes equal-cost multipath
                 nexthops";
            }
          }
        }
        leaf remote-lfa {
          when "local-name(../../../..) = 'ipv4-conf'" {
            description
              "remote-lfa option just exist under address-family
               ipv4 unicast.";
          }
          type empty;
          description
            "Configure Remote LFA computation";
        }
      }
    }
    /*
    ti-lfa [ backup |  [ protect { link-only } ] | [ protect {
     link-only | node-only } ] [ segment-limit (limit-value) ] ]
    */
    container ti-lfa {
      when "local-name(..) = 'unicast' and contains(../../../.."
      + "/isisrouter6000:interface, '@local')" {
        description
          "tilfa is configurable on unicast only for both
           address-family ipv4 and address-family ipv6.";
      }
      presence "";
      description
        "Configure Loop Free Alternate (TILFA) computation";
      leaf backup {
        type boolean;
        default "true";
        description
          "Enable/Disable backup";
      }
      container protect-link-only {
        status obsolete;
        description
          "container protect-link-only.";
        leaf protect-link-only {
          type empty;
          description
            "Only link protecting neighbors will be chosen as
             TILFAs";
        }
      }
      container protect {
        description
          "Configure TILFA protection";
        leaf protect {
          type enumeration {
            enum link-only {
              value 0;
              description
                "Only link protecting neighbors will be chosen
                 as TILFAs";
            }
            enum node-only {
              value 1;
              description
                "Only node protecting neighbors will be chosen
                 as TILFAs";
            }
          }
          description
            "Configure TILFA protection constraints";
        }
        leaf segment-limit {
          type uint8 {
            range "0..2";
          }
          default "2";
          description
            "Configure TILFA segment limit";
        }
      }
    }
    /*
    tag (tag-val)
    */
    leaf tag {
      type uint32 {
        range "1..4294967295";
      }
      description
        "configure route tag";
    }
    /*
    prefix-sid-conf-new { srv6 locator (locid) }
    */
    container prefix-sid-conf-new {
      when "local-name(..) = 'unicast' and local-name(../..) = 'ipv6'"
      + " and not(../../../../../../../ctxr6k:vpn-conf)" {
        description
          "prefix-sid srv6 option is applicable only for
           address-family ipv6 unicast";
      }
      description
        "Configure prefix-segment identifier for the interface";
      container srv6 {
        description
          "Configure segment routing srv6";
        list locator {
          key "locator";
          description
            "Locator";
          leaf locator {
            type string;
            description
              "Locator ID";
          }
        }
      }
    }
    /*
    prefix-sid-conf index (global-value) [ node ] [ explicit-
     null | php ]
    */
    container prefix-sid-conf-index {
      when "local-name(..) = 'unicast' and not(../../../../../../.."
      + "/ctxr6k:vpn-conf)" {
        description
          "prefix-sid option exists under both address-family
           ipv4 unicast and address-family ipv6 unicast.";
      }
      presence "";
      description
        "Index into the SRGB range";
      leaf global-value {
        type uint32 {
          range "0..131071";
        }
        mandatory true;
        description
          "Segment identifier";
      }
      leaf node {
        type empty;
        description
          "Configure as a node-segment identifier";
      }
      leaf prefix-sid-conf-index-opt {
        type enumeration {
          enum explicit-null {
            value 0;
            description
              "Enable explicit-NULL operation";
          }
          enum php {
            value 1;
            description
              "Enable penultimate-hop pop operation";
          }
        }
        description
          "leaf prefix-sid-conf-index-opt.";
      }
    }
    /*
    adjacency-sid-new srv6 { locator (locid) }
    */
    container adjacency-sid-new-srv6 {
      when "local-name(..) = 'unicast' and local-name(../..) = 'ipv6'"
      + " and not(../../../../../../../ctxr6k:vpn-conf)" {
        description
          "adjacency-sid srv6 option is applicable only for
           address-family ipv6 unicast";
      }
      description
        "Configure segment routing srv6";
      list locator {
        key "locator";
        max-elements 1;
        description
          "Locator";
        leaf locator {
          type string;
          description
            "Locator ID";
        }
      }
    }
    /*
    adjacency-sid srv6 locator (locid)
    */
    container adjacency-sid-srv6-locator {
      when "local-name(..) = 'unicast' and local-name(../..) = 'ipv6'"
      + " and not(../../../../../../../ctxr6k:vpn-conf)" {
        description
          "adjacency-sid srv6 option is applicable only for
           address-family ipv6 unicast";
      }
      status obsolete;
      description
        "Locator";
      leaf locid {
        type string;
        mandatory true;
        status obsolete;
        description
          "Locator ID";
      }
    }
    /*
    metricpassive { level-1 (metric-value) | level-2 (metric-
     value) }
    */
    container metricpassive {
      when "../../../../passive-interface" {
        description
          "Configure a metric for passive interface only";
      }
      description
        "Configure a metric for passive interface only";
      leaf level-1 {
        type uint32 {
          range "1..16777215";
        }
        default "1";
        description
          "Configure metric value for level-1 only";
      }
      leaf level-2 {
        type uint32 {
          range "1..16777215";
        }
        default "1";
        description
          "Configure metric value for level-2 only";
      }
    }
  }

  augment "/ctxsr6k:contexts/ctxr6k:context/ctxr6k:router" {
    description
      "ericsson-isis";
    /*
    isis (isis-tag)
    */
    list isis {
      key "isis";
      description
        "ISO IS-IS";
      leaf isis {
        type string;
        description
          "IS-IS protocol instance name";
      }
      uses isis-grp;
    }
  }

}
