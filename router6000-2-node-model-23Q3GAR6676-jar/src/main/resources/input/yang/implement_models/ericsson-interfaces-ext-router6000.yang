module ericsson-interfaces-ext-router6000 {
  yang-version "1";

  namespace "urn:rdns:com:ericsson:oammodel:ericsson-interfaces-ext-router6000";

  prefix "ifxrouter6000";

  import ietf-inet-types {
    prefix "inet";
  }

  import ericsson-types-router6000 {
    prefix "typesrouter6000";
  }

  import ietf-interfaces {
    prefix "if";
  }

  import ericsson-contexts-router6000 {
    prefix "ctxsr6k";
  }

  import ericsson-context-router6000 {
    prefix "ctxr6k";
  }

  import iana-if-type {
    prefix "ianaift";
  }

  import ietf-yang-types {
    prefix "yang";
  }

  import ericsson-yang-extensions {
    prefix "yexte";
  }

  import ericsson-notifications {
    prefix notife;
  }

  organization
    "Ericsson AB";

  contact
    "Web:   <http://www.ericsson.com>";

  description
    "ericsson-interfaces-ext-router6000
     Copyright (c) 2022 Ericsson AB.
     All rights reserved";

  revision "2022-07-20" {
    description
      "keep the ip unnumbered action with cli";
    reference
      "rfc6020";
    yexte:version "3";
    yexte:release "11";
    yexte:correction "1";
  }

  revision "2022-04-22" {
    description
      "modify interface mtu max value and remove if-feature";
    reference
      "rfc6020";
    yexte:version "3";
    yexte:release "11";
    yexte:correction "0";
  }

  revision "2022-03-11" {
    description
      "Add acl logging";
    reference
      "rfc6020";
    yexte:version "3";
    yexte:release "10";
    yexte:correction "0";
  }

  revision "2022-01-04" {
    description
      "Add new CLI to configure periodic arp/ns refresh-interval";
    reference
      "rfc6020";
    yexte:version "3";
    yexte:release "9";
    yexte:correction "0";
  }

  revision "2021-12-20" {
    description
      "add evpn default gateway command";
    reference
      "rfc6020";
    yexte:version "3";
    yexte:release "8";
    yexte:correction "0";
  }

  revision "2021-08-20" {
    description
      "add notife for config_status";
    reference
      "rfc6020";
    yexte:version "3";
    yexte:release "7";
    yexte:correction "0";
  }

  revision "2021-06-01" {
    description
      "add config-status to interfaces-state";
    reference
      "rfc6020";
    yexte:version "3";
    yexte:release "6";
    yexte:correction "0";
  }

  revision "2020-12-31" {
    description
      "strict ip validation for p2p interface";
    reference
      "rfc6020";
    yexte:version "3";
    yexte:release "5";
    yexte:correction "0";
  }

  revision "2020-12-09" {
    description
      "add model for ipv6 pool dhcpv6 ";
    reference
      "rfc6020";
    yexte:version "3";
    yexte:release "4";
    yexte:correction "1";
  }

  revision "2020-11-19" {
    description
      "add dual-stack counters ";
    reference
      "rfc6020";
    yexte:version "3";
    yexte:release "3";
    yexte:correction "0";
  }

  revision "2019-07-09" {
    description
      "updated model for ip source-addres ";
    reference
      "rfc6020";
    yexte:version "3";
    yexte:release "2";
    yexte:correction "0";
  }

  revision "2019-04-30" {
    description
      "corrected model for ip address dhcp";
    reference
      "rfc6020";
    yexte:version "3";
    yexte:release "1";
    yexte:correction "0";
  }

  revision "2018-11-27" {
    description
      "remove ipos choice description";
    reference
      "rfc6020";
    yexte:version "3";
    yexte:release "0";
    yexte:correction "2";
  }

  revision "2018-06-22" {
    description
      "remove nat under interface modeling";
    reference
      "rfc6020";
    yexte:version "3";
    yexte:release "0";
    yexte:correction "1";
  }

  revision "2018-06-05" {
    description
      "Change model namespace";
    reference
      "rfc6020";
    yexte:version "3";
    yexte:release "0";
    yexte:correction "0";
  }

  revision "2018-03-07" {
    description
      "nat under interface modeling";
    reference
      "rfc6020";
    yexte:version "2";
    yexte:release "1";
    yexte:correction "0";
  }

  revision "2018-01-10" {
    description
      "Description 'IPV6' shouldn't display when configuring
       l3-interface ip verify-unicast-source-reachable-via";
    reference
      "rfc6020";
    yexte:version "2";
    yexte:release "0";
    yexte:correction "5";
  }

  revision "2017-11-29" {
    description
      "access-group in command ip and ipv6 should be placed
       after any and receive";
    reference
      "rfc6020";
    yexte:version "2";
    yexte:release "0";
    yexte:correction "4";
  }

  revision "2017-11-13" {
    description
      "SSR-8503 Support missed commands in YANG model -
       intercontext interface";
    reference
      "rfc6020";
    yexte:version "1";
    yexte:release "0";
    yexte:correction "4";
  }

  revision "2017-11-08" {
    description
      "IPOS-18022 ip reroute: bfd and truck should cover each
       other";
    reference
      "rfc6020";
    yexte:version "1";
    yexte:release "0";
    yexte:correction "3";
  }

  revision "2017-09-29" {
    description
      "update revision for ip change";
    reference
      "rfc6020";
    yexte:version "1";
    yexte:release "0";
    yexte:correction "2";
  }

  revision "2017-07-27" {
    description
      "IPOS-13391 ip reroute: connot delete ip reroute by rpc
       message.";
    reference
      "rfc6020";
    yexte:version "1";
    yexte:release "0";
    yexte:correction "1";
  }

  revision "2017-07-09" {
    description
      "Add command 'ip reroute' and 'ip multicast' under
       l3-interface.";
    reference
      "rfc6020";
    yexte:version "1";
    yexte:release "0";
    yexte:correction "0";
  }

  revision "2017-06-20" {
    description
      "Add if type applicationLoopback under l3-interface.";
    reference
      "rfc6020";
  }

  revision "2017-06-15" {
    description
      "Add 'when' condition for 'pool' in command 'ip pool'.";
    reference
      "rfc6020";
  }

  revision "2017-05-25" {
    description
      "Add if type p2pOverLan under l3-interface.";
    reference
      "rfc6020";
  }

  revision "2017-05-24" {
    description
      "IPOS-11149:context and interface new command";
    reference
      "rfc6020";
  }

  revision "2017-05-23" {
    description
      "IPOS-10756 change source address all condition";
    reference
      "rfc6020";
  }

  revision "2017-04-27" {
    description
      "IPOS-8528 Add ip source address model under
       l3-interface.";
    reference
      "rfc6020";
  }

  revision "2017-03-30" {
    description
      "IPOS-8033 [interface]The model ip access-group in
       interface have some issue.";
    reference
      "rfc6020";
  }

  revision "2016-10-20" {
    description
      "Add the ipv4/v6 type to fix the ipv4 and v6 addresses
       can't be set successfully.";
    reference
      "rfc6020";
  }

  revision "2016-07-29" {
    description
      "remove the if-feature of ipv6 adress added on
       2016-07-08.";
    reference
      "rfc6020";
  }

  revision "2016-07-08" {
    description
      "remove ipv6 verify and secondary address.";
    reference
      "rfc6020";
  }

  revision "2016-03-29" {
    description
      "For CLI2Yang models data node sequence change.";
    reference
      "rfc6020";
  }

  revision "2015-12-07" {
    description
      "initial revision";
    reference
      "rfc6020";
  }

  feature multicast-output {
    description
      "This feature indicates that the device supports
       multicast-output in interface.";
  }

  feature clear-df {
    description
      "This feature indicates that the device supports clear-df
       in interface.";
  }

  feature mtu {
    description
      "This feature indicates that the device supports mtu in
       interface.";
  }

  feature snmp-dhcp-server {
    description
      "This feature indicates that the device supports
       snmp-dhcp-server in interface.";
  }

  feature snmp-flow-ip {
    description
      "This feature indicates that the device supports
       snmp-flow-ip in interface.";
  }

  feature snmp-icmp-time-exceed {
    description
      "This feature indicates that the device supports
       snmp-icmp-time-exceed in interface.";
  }

  feature igmp {
    description
      "This feature indicates that the device supports igmp in
       interface.";
  }

  feature trafic-index-accounting {
    description
      "This feature indicates that the device supports
       trafic-index-accounting in interface.";
  }

  feature icr {
    description
      "This feature indicates that the device supports icr in
       interface.";
  }

  feature ipv6-mtu {
    description
      "This feature indicates that the device supports ipv6 mtu
       in interface.";
  }

  feature packet-logging {
    description
      "This feature indicates that the device supports packet
       logging in interface.";
  }

  feature pbr {
    description
      "This feature indicates that the device supports pbr in
       interface.";
  }

  feature ipv6 {
    description
      "This feature indicates that the device supports ipv6
       address in interface.";
  }

  feature pool {
    description
      "This feature indicates that the device supports ip pool
       in interface.";
  }


    identity p2pOverLan {
      base if:interface-type;
      description
        "interface as point-to-point independent of circuit type";
    }


    identity applicationLoopback {
      base if:interface-type;
      description
        "interface as an application loopback interface type";
    }


    identity intercontext {
      base if:interface-type;
      description
        "interface as an inter-context interface type";
    }

    typedef interface_config_type {
        type enumeration {
            enum configured {
                value 1;
                description "interface configured";
            }
            enum unconfigured {
                value 2;
                description "interface unconfigured";
            }
            enum unavailable {
                value 3;
                description "interface unavailable";
            }
            enum no-license {
                value 4;
                description "interface no-license";
            }
            enum no-card {
                value 5;
                description "interface no-card ";
            }
        }
        description "interface state type";
    }

  grouping if-grp {
    description
      "Interface configuration mode";
    /*
    multicast output [ accept-unknown-mac ]
    */
    container multicast-output {
      if-feature multicast-output;
      presence "";
      description
        "Enable interface for sRMR Multicast output";
      leaf accept-unknown-mac {
        type empty;
        description
          "Accept joins from unknown MAC addresses";
      }
    }
    /*
     ipv6 { mtu (mtu-len) | link-local [ (local-addr) ] | {
      address { addr-primary (addr) | addr-secondary (addr) } |
      unnumbered (unnumbered-if) } | < access-group (cls-name)
      (direction) [ count ] [ log ] > | verify unicast source
      reachable-via { < any [ allow-default ] < [ access-group ]
      (access-list) [ acl-count ] > > | < receive [ allow-default
      ]  < [ access-group ] (access-list) [ acl-count] > > } | <
      pool dhcpv6 (first-prefix) (last-prefix) [ name (name-str) ]
      [ threshold { absolute [ falling (val-1) { trap { log [
      (val-2) { trap [ log ] | log [ trap ] } ] | (val-3) { trap [
      log ] | log [ trap ] } } | log { trap [ (val-4) { trap [ log
      ] | log [ trap ] } ] | (val-5) { trap [ log ] | log [ trap ]
      } } } ] | percentage [falling (val-6) { trap { log [ (val-7)
      { trap [ log ] | log [ trap ] } ] | (val-8) { trap [ log ] |
      log [ trap ] } } | log { trap [ (val-9) { trap [ log ] | log
      [ trap ] } ] | (val-10) { trap [ log ] | log [ trap ] } } }
      ] } ] > }
    */
    container ipv6 {
      description
        "IPv6 configuration command";
      leaf mtu {
        type uint16 {
          range "1280..9600";
        }
        description
          "Set IP mtu size";
      }
      container link-local {
        presence "";
        description
          "Configure a IPV6 link local address";
        leaf local-addr {
          type inet:ipv6-address;
          description
            "Link local IPv6 address";
        }
      }
      choice ipv6-choice {
        case address {
          container address {
            description
              "IP address to be configured";
            leaf addr-primary {
              type typesrouter6000:ipv6-address-mask;
              description
                "IP address to be configured";
            }
            list addr-secondary {
              key "addr-secondary";
              max-elements 31;
              description
                "IP address to be configured";
              leaf addr-secondary {
                type typesrouter6000:ipv6-address-mask;
                must "../../addr-primary" {
                  error-message "Configure a primary IP address "
                  + "before configuring a v6 secondary address";
                  description
                    "";
                }
                description
                  "IPv6 address";
              }
            }
          }
        }
        case unnumbered {
          leaf unnumbered {
            type string;
            description
              "IP unnumbered: address to be borrowed from
               another interface";
          }
        }
      }
      list access-group {
        key "direction";
        description
          "Apply packet access control";
        leaf direction {
          type typesrouter6000:access_group_dir;
          description
            "The direction ACL list to appiled in the interface";
        }
        leaf cls-name {
          type string {
            pattern '(\S+)|(\S+(\s\S+)*)';
          }
          mandatory true;
          description
            "access list name (up to 10 names)";
        }
        leaf count {
          type empty;
          description
            "Configure access list packet counting";
        }
        leaf log {
          when "(../direction='in')" {
            description
              "The direction of acl logging can only configured
               in the inbound";
          }
          type empty;
          description
            "Configure access list packet logging";
        }
      }
      container verify-unicast-source-reachable-via {
        if-feature pbr;
        description
          "Specify the validation for the source address";
        choice verify-unicast-source-reachable-via-choice {
          case any {
            container any {
              presence "";
              description
                "Source IPv6 address can be reached by any
                 interface";
              leaf allow-default {
                type empty;
                description
                  "Allow RPF to lookup the default route for
                   verification";
              }
              container access-group {
                presence "";
                description
                  "Apply access control to RPF IPv6 source
                   address selection";
                leaf access-list {
                  type string;
                  mandatory true;
                  description
                    "IPv6 access list name(s) (up to 10 enclosed
                     in quotes)";
                }
                leaf acl-count {
                  type empty;
                  description
                    "Enable IPv6 access list match counting";
                }
              }
            }
          }
          case receive {
            container receive {
              presence "";
              description
                "Source address must be reachable through the
                 incoming interface";
              leaf allow-default {
                type empty;
                description
                  "Allow RPF to lookup the default route for
                   verification";
              }
              container access-group {
                presence "";
                description
                  "Apply access control to RPF IPv6 source
                   address selection";
                leaf access-list {
                  type string;
                  mandatory true;
                  description
                    "IPv6 access list name(s) (up to 10 enclosed
                     in quotes)";
                }
                leaf acl-count {
                  type empty;
                  description
                    "Enable IPv6 access list match counting";
                }
              }
            }
          }
        }
      }
      list pool-dhcpv6 {
        key "first-prefix";
        description
          "Configure DHCPv6 pool attributes";
        leaf first-prefix {
          type typesrouter6000:pool-dhcpv6-address-mask;
          description
            "First IPv6 address or prefix in pool in
             colon-separated notation or notation/length";
        }
        leaf last-prefix {
          type typesrouter6000:pool-dhcpv6-address-mask;
          mandatory true;
          description
            "Last IPv6 address or prefix in pool in
             colon-separated notation or notation/length";
        }
        leaf name {
          type string;
          description
            "Configure IPv6 pool name";
        }
        container threshold {
          description
            "Configure IPv6 pool threshold";
          choice threshold {
            case absolute {
              container absolute {
                presence "";
                description
                  "Configure absolute values for threshold";
                container absolute-opt {
                  description
                    "container absolute-opt.";
                  leaf falling {
                    type empty;
                    mandatory true;
                    description
                      "Configure falling threshold";
                  }
                  leaf val-1 {
                    type uint16 {
                      range "0..65535";
                    }
                    mandatory true;
                    description
                      "Falling threshold value";
                  }
                  choice absolute-opt-choice {
                    case trap {
                      container trap {
                        presence "";
                        description
                          "Generate SNMP trap";
                        choice trap {
                          case log {
                            container log {
                              presence "";
                              description
                                "Generate log message";
                              container log-opt {
                                description
                                  "container log-opt.";
                                leaf val-2 {
                                  type uint16 {
                                    range "0..65535";
                                  }
                                  mandatory true;
                                  description
                                    "Configure a second Falling
                                     threshold value";
                                }
                                choice log-opt-choice {
                                  case trap {
                                    container trap {
                                      presence "";
                                      description
                                        "Generate SNMP trap";
                                      leaf log {
                                        type empty;
                                        description
                                          "Generate log message";
                                      }
                                    }
                                  }
                                  case log {
                                    container log {
                                      presence "";
                                      description
                                        "Generate log message";
                                      leaf trap {
                                        type empty;
                                        description
                                          "Generate SNMP trap";
                                      }
                                    }
                                  }
                                }
                              }
                            }
                          }
                          case val-3 {
                            container val-3 {
                              description
                                "container val-3.";
                              leaf val-3 {
                                type uint16 {
                                  range "0..65535";
                                }
                                mandatory true;
                                description
                                  "Configure a second Falling
                                   threshold value";
                              }
                              choice val-3-choice {
                                case trap {
                                  container trap {
                                    presence "";
                                    description
                                      "Generate SNMP trap";
                                    leaf log {
                                      type empty;
                                      description
                                        "Generate log message";
                                    }
                                  }
                                }
                                case log {
                                  container log {
                                    presence "";
                                    description
                                      "Generate log message";
                                    leaf trap {
                                      type empty;
                                      description
                                        "Generate SNMP trap";
                                    }
                                  }
                                }
                              }
                            }
                          }
                        }
                      }
                    }
                    case log {
                      container log {
                        presence "";
                        description
                          "Generate log message";
                        choice log {
                          case trap {
                            container trap {
                              presence "";
                              description
                                "Generate SNMP trap";
                              container trap-opt {
                                description
                                  "container trap-opt.";
                                leaf val-4 {
                                  type uint16 {
                                    range "0..65535";
                                  }
                                  mandatory true;
                                  description
                                    "Configure a second Falling
                                     threshold value";
                                }
                                choice trap-opt-choice {
                                  case trap {
                                    container trap {
                                      presence "";
                                      description
                                        "Generate SNMP trap";
                                      leaf log {
                                        type empty;
                                        description
                                          "Generate log message";
                                      }
                                    }
                                  }
                                  case log {
                                    container log {
                                      presence "";
                                      description
                                        "Generate log message";
                                      leaf trap {
                                        type empty;
                                        description
                                          "Generate SNMP trap";
                                      }
                                    }
                                  }
                                }
                              }
                            }
                          }
                          case val-5 {
                            container val-5 {
                              description
                                "container val-5.";
                              leaf val-5 {
                                type uint16 {
                                  range "0..65535";
                                }
                                mandatory true;
                                description
                                  "Configure a second Falling
                                   threshold value";
                              }
                              choice val-5-choice {
                                case trap {
                                  container trap {
                                    presence "";
                                    description
                                      "Generate SNMP trap";
                                    leaf log {
                                      type empty;
                                      description
                                        "Generate log message";
                                    }
                                  }
                                }
                                case log {
                                  container log {
                                    presence "";
                                    description
                                      "Generate log message";
                                    leaf trap {
                                      type empty;
                                      description
                                        "Generate SNMP trap";
                                    }
                                  }
                                }
                              }
                            }
                          }
                        }
                      }
                    }
                  }
                }
              }
            }
            case percentage {
              container percentage {
                presence "";
                description
                  "Configure percentage values for threshold";
                container percentage-opt {
                  description
                    "container percentage-opt.";
                  leaf falling {
                    type empty;
                    mandatory true;
                    description
                      "Configure falling threshold";
                  }
                  leaf val-6 {
                    type uint8 {
                      range "0..100";
                    }
                    mandatory true;
                    description
                      "Falling threshold value";
                  }
                  choice percentage-opt-choice {
                    case trap {
                      container trap {
                        presence "";
                        description
                          "Generate SNMP trap";
                        choice trap {
                          case log {
                            container log {
                              presence "";
                              description
                                "Generate log message";
                              container log-opt {
                                description
                                  "container log-opt.";
                                leaf val-7 {
                                  type uint8 {
                                    range "0..100";
                                  }
                                  mandatory true;
                                  description
                                    "Configure a second Falling
                                     threshold value";
                                }
                                choice log-opt-choice {
                                  case trap {
                                    container trap {
                                      presence "";
                                      description
                                        "Generate SNMP trap";
                                      leaf log {
                                        type empty;
                                        description
                                          "Generate log message";
                                      }
                                    }
                                  }
                                  case log {
                                    container log {
                                      presence "";
                                      description
                                        "Generate log message";
                                      leaf trap {
                                        type empty;
                                        description
                                          "Generate SNMP trap";
                                      }
                                    }
                                  }
                                }
                              }
                            }
                          }
                          case val-8 {
                            container val-8 {
                              description
                                "container val-8.";
                              leaf val-8 {
                                type uint8 {
                                  range "0..100";
                                }
                                mandatory true;
                                description
                                  "Configure a second Falling
                                   threshold value";
                              }
                              choice val-8-choice {
                                case trap {
                                  container trap {
                                    presence "";
                                    description
                                      "Generate SNMP trap";
                                    leaf log {
                                      type empty;
                                      description
                                        "Generate log message";
                                    }
                                  }
                                }
                                case log {
                                  container log {
                                    presence "";
                                    description
                                      "Generate log message";
                                    leaf trap {
                                      type empty;
                                      description
                                        "Generate SNMP trap";
                                    }
                                  }
                                }
                              }
                            }
                          }
                        }
                      }
                    }
                    case log {
                      container log {
                        presence "";
                        description
                          "Generate log message";
                        choice log {
                          case trap {
                            container trap {
                              presence "";
                              description
                                "Generate SNMP trap";
                              container trap-opt {
                                description
                                  "container trap-opt.";
                                leaf val-9 {
                                  type uint8 {
                                    range "0..100";
                                  }
                                  mandatory true;
                                  description
                                    "Configure a second Falling
                                     threshold value";
                                }
                                choice trap-opt-choice {
                                  case trap {
                                    container trap {
                                      presence "";
                                      description
                                        "Generate SNMP trap";
                                      leaf log {
                                        type empty;
                                        description
                                          "Generate log message";
                                      }
                                    }
                                  }
                                  case log {
                                    container log {
                                      presence "";
                                      description
                                        "Generate log message";
                                      leaf trap {
                                        type empty;
                                        description
                                          "Generate SNMP trap";
                                      }
                                    }
                                  }
                                }
                              }
                            }
                          }
                          case val-10 {
                            container val-10 {
                              description
                                "container val-10.";
                              leaf val-10 {
                                type uint8 {
                                  range "0..100";
                                }
                                mandatory true;
                                description
                                  "Configure a second Falling
                                   threshold value";
                              }
                              choice val-10-choice {
                                case trap {
                                  container trap {
                                    presence "";
                                    description
                                      "Generate SNMP trap";
                                    leaf log {
                                      type empty;
                                      description
                                        "Generate log message";
                                    }
                                  }
                                }
                                case log {
                                  container log {
                                    presence "";
                                    description
                                      "Generate log message";
                                    leaf trap {
                                      type empty;
                                      description
                                        "Generate SNMP trap";
                                    }
                                  }
                                }
                              }
                            }
                          }
                        }
                      }
                    }
                  }
                }
              }
            }
          }
        }
      }
    }
    /*
    ip { mtu (mtu-len) |  { reroute (reroute-dest)  [ bfd [
     track (reroute-eti2) ] | track (reroute-eti) [ bfd ] ] }  |
     clear-df | { < address { addr-primary (addr) [ tag  (tag-
     num)  ] | addr-primary-conf (addr) [ tag (tag-num) ] | <
     addr-secondary (addr)  [ tag  (tag-num)  ]> | < addr-
     secondary-conf (addr)  [ tag  (tag-num) ]> }  > | unnumbered
     (unnumbered-if) }  | source-address { < options [ snmp ] [
     telnet ] [ ssh ] [ dhcp-server ] [ syslog ] [ radius ] [
     tacacs-plus ] [ tftp ] [ ftp ] [ icmp-dest-unreachable ] [
     icmp-time-exceed ] [ netop ] [ flow-ip ] [ ldap ] [ http ] [
     cmpv2 ] > | all } |< access-group  (cls-name) (direction) [
     count ] [ log ] > | verify unicast source reachable-via { <
     any [ rpf-count ] [ allow-default ] <[ access-group ]
     (access-list) [ acl-count ] > >| < receive [ allow-default ]
     < [ access-group ] (access-list) [ acl-count ] > > } | tcp
     mss replace (direction) (mss-size) | icmp suppress packet-
     too-big |  < pool { (pool-addr) | <(start-addr) to (end-
     addr) > } [ name (name-str) ] [ falling-threshold (falling-
     threshold-size) { trap [ log ] | log [ trap ] } ] > }
    */
    container ip {
      description
        "IP configuration command";
      leaf mtu {
        type uint16 {
          range "256..9600";
        }
        description
          "Set IP mtu size";
      }
      container reroute {
        presence "";
        description
          "Specify the reroute configuration";
        leaf reroute-dest {
          type inet:ipv4-address;
          mandatory true;
          description
            "Destination of peer chassis";
        }
        choice reroute-opt {
          case bfd {
            container bfd {
              presence "";
              description
                "BFD monitoring";
              leaf track {
                type string;
                description
                  "Configure ETI tracking";
              }
            }
          }
          case track {
            container track {
              presence "";
              description
                "Configure ETI tracking";
              leaf reroute-eti {
                type string;
                mandatory true;
                description
                  "ETI object name of ip reroute";
              }
              leaf bfd {
                type empty;
                description
                  "BFD monitoring";
              }
            }
          }
        }
      }
      leaf clear-df {
        if-feature clear-df;
        type empty;
        description
          "Ignore DF bit on IP packets and fragment if needed";
      }
      choice ip-choice {
        case address {
          container address {
            description
              "IP address to be configured";
            container addr-primary {
              presence "";
              status obsolete;
              description
                "IP address to be configured";
              leaf addr {
                type typesrouter6000:ipos-ip-prefix;
                mandatory true;
                description
                  "Address followed by mask or prefix length";
              }
              leaf tag {
                type uint32 {
                  range "0..4294967295";
                }
                default "0";
                description
                  "Route tag";
              }
            }
            container addr-primary-conf {
              presence "";
              description
                "IP address to be configured";
              leaf addr {
                type typesrouter6000:r6000-ip-prefix;
                mandatory true;
                description
                  "Address followed by mask or prefix length";
              }
              leaf tag {
                type uint32 {
                  range "0..4294967295";
                }
                default "0";
                description
                  "Route tag";
              }
            }
            list addr-secondary {
              must "../addr-primary/addr" {
                error-message "Configure a primary IP address "
                + "before configuring a v4 secondary address";
                description
                  "Configure a primary IP address before
                   configuring a secondary address";
              }
              key "addr";
              max-elements 31;
              status obsolete;
              description
                "IP address to be configured";
              leaf addr {
                type typesrouter6000:ipos-ip-prefix;
                description
                  "Address followed by mask or prefix length";
              }
              leaf tag {
                type uint32 {
                  range "0..4294967295";
                }
                default "0";
                description
                  "Route tag";
              }
            }
            list addr-secondary-conf {
              must "../addr-primary-conf/addr" {
                error-message "Configure a primary IP address "
                + "before configuring a v4 secondary address";
                description
                  "Configure a primary IP address before
                   configuring a secondary address";
              }
              key "addr";
              max-elements 31;
              description
                "IP address to be configured";
              leaf addr {
                type typesrouter6000:ipos-ip-prefix;
                description
                  "Address followed by mask or prefix length";
              }
              leaf tag {
                type uint32 {
                  range "0..4294967295";
                }
                default "0";
                description
                  "Route tag";
              }
            }
          }
        }
        case unnumbered {
          leaf unnumbered {
            type string;
            description
              "IP unnumbered: address to be borrowed from
               another interface";
          }
        }
      }
      container source-address {
        description
          "Specify the source interface";
        choice source-address {
          case options {
            container options {
              description
                "container options.";
              leaf snmp {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:snmp)<2" {
                  error-message "Conflict exists,snmp has "
                  + "already been set under different interface "
                  + "associated with the same context.";
                  description
                    "Conflict exists,snmp has already been set
                     under different interface associated with
                     the same context. ";
                }
                description
                  "Configure source-interface for snmp";
              }
              leaf telnet {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:telnet)<2" {
                  error-message "Conflict exists,telnet has "
                  + "already been set under different interface "
                  + "associated with the same context.";
                  description
                    "Conflict exists,telnet has already been set
                     under different interface associated with
                     the same context. ";
                }
                description
                  "Configure source-interface for telnet";
              }
              leaf ssh {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:ssh)<2" {
                  error-message "Conflict exists,ssh has already "
                  + "been set under different interface associated "
                  + "with the same context.";
                  description
                    "Conflict exists,ssh has already been set
                     under different interface associated with
                     the same context. ";
                }
                description
                  "Configure source-interface for ssh/sftp/scp";
              }
              leaf dhcp-server {
                type empty;
                must "count(/if:interfaces/if:interface/ifxroute"
                + "r6000:l3-interface[ifxrouter6000:context=current"
                + "()/../../../../ifxrouter6000:context]/ifxrouter6"
                + "000:ip/ifxrouter6000:source-"
                + "address/ifxrouter6000:options/ifxrouter6000"
                + ":dhcp-server)<2" {
                  error-message "Conflict exists,dhcp-server has "
                  + "already been set under different interface "
                  + "associated with the same context.";
                  description
                    "Conflict exists,dhcp-server has already
                     been set under different interface
                     associated with the same context. ";
                }
                description
                  "Configure source-interface for dhcp server";
              }
              leaf syslog {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:syslog)<2" {
                  error-message "Conflict exists,syslog has "
                  + "already been set under different interface "
                  + "associated with the same context.";
                  description
                    "Conflict exists,syslog has already been set
                     under different interface associated with
                     the same context. ";
                }
                description
                  "Configure source-interface for syslog";
              }
              leaf radius {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:radius)<2" {
                  error-message "Conflict exists,radius has "
                  + "already been set under different interface "
                  + "associated with the same context.";
                  description
                    "Conflict exists,radius has already been set
                     under different interface associated with
                     the same context. ";
                }
                description
                  "Configure source-interface for radius";
              }
              leaf tacacs-plus {
                type empty;
                must "count(/if:interfaces/if:interface/ifxroute"
                + "r6000:l3-interface[ifxrouter6000:context=current"
                + "()/../../../../ifxrouter6000:context]/ifxrouter6"
                + "000:ip/ifxrouter6000:source-"
                + "address/ifxrouter6000:options/ifxrouter6000"
                + ":tacacs-plus)<2" {
                  error-message "Conflict exists,tacacs+ has "
                  + "already been set under different interface "
                  + "associated with the same context.";
                  description
                    "Conflict exists,tacacs+ has already been
                     set under different interface associated
                     with the same context. ";
                }
                description
                  "Configure source-interface for tacacs+";
              }
              leaf tftp {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:tftp)<2" {
                  error-message "Conflict exists,tftp has "
                  + "already been set under different interface "
                  + "associated with the same context.";
                  description
                    "Conflict exists,tftp has already been set
                     under different interface associated with
                     the same context. ";
                }
                description
                  "Configure source-interface for tftp";
              }
              leaf ftp {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:ftp)<2" {
                  error-message "Conflict exists,ftp has already "
                  + "been set under different interface associated "
                  + "with the same context.";
                  description
                    "Conflict exists,ftp has already been set
                     under different interface associated with
                     the same context. ";
                }
                description
                  "Configure source-interface for ftp";
              }
              leaf icmp-dest-unreachable {
                type empty;
                must "count(/if:interfaces/if:interface/ifxroute"
                + "r6000:l3-interface[ifxrouter6000:context=current"
                + "()/../../../../ifxrouter6000:context]/ifxrouter6"
                + "000:ip/ifxrouter6000:source-"
                + "address/ifxrouter6000:options/ifxrouter6000"
                + ":icmp-dest-unreachable)<2" {
                  error-message "Conflict exists,icmp-dest- "
                  + "unreachable has already been set under "
                  + "different interface associated with the same "
                  + "context.";
                  description
                    "Conflict exists,icmp-dest-unreachable has
                     already been set under different interface
                     associated with the same context. ";
                }
                description
                  "Configure source-interface for
                   icmp-dest-unreachable";
              }
              leaf icmp-time-exceed {
                type empty;
                must "count(/if:interfaces/if:interface/ifxroute"
                + "r6000:l3-interface[ifxrouter6000:context=current"
                + "()/../../../../ifxrouter6000:context]/ifxrouter6"
                + "000:ip/ifxrouter6000:source-"
                + "address/ifxrouter6000:options/ifxrouter6000"
                + ":icmp-time-exceed)<2" {
                  error-message "Conflict exists,icmp-time- "
                  + "exceed has already been set under different "
                  + "interface associated with the same context.";
                  description
                    "Conflict exists,icmp-time-exceed has
                     already been set under different interface
                     associated with the same context. ";
                }
                description
                  "Configure source-interface for
                   icmp-time-exceed";
              }
              leaf netop {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:netop)<2" {
                  error-message "Conflict exists,netop has "
                  + "already been set under different interface "
                  + "associated with the same context.";
                  description
                    "Conflict exists,netop has already been set
                     under different interface associated with
                     the same context. ";
                }
                status obsolete;
                description
                  "Configure source-interface for netop";
              }
              leaf flow-ip {
                type empty;
                must "count(/if:interfaces/if:interface/ifxroute"
                + "r6000:l3-interface[ifxrouter6000:context=current"
                + "()/../../../../ifxrouter6000:context]/ifxrouter6"
                + "000:ip/ifxrouter6000:source-"
                + "address/ifxrouter6000:options/ifxrouter6000"
                + ":flow-ip)<2" {
                  error-message "Conflict exists,flow-ip has "
                  + "already been set under different interface "
                  + "associated with the same context.";
                  description
                    "Conflict exists,flow-ip has already been
                     set under different interface associated
                     with the same context. ";
                }
                status obsolete;
                description
                  "Configure source-interface for rflow";
              }
              leaf ldap {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:ldap)<2" {
                  error-message "Conflict exists,ldap has "
                  + "already been set under different interface "
                  + "associated with the same context.";
                  description
                    "Conflict exists,ldap has already been set
                     under different interface associated with
                     the same context. ";
                }
                description
                  "Configure source-interface for ldap";
              }
              leaf http {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:http)<2" {
                  error-message "Conflict exists,http has "
                  + "already been set under different interface "
                  + "associated with the same context.";
                  description
                    "Conflict exists,http has already been set
                     under different interface associated with
                     the same context. ";
                }
                description
                  "Configure source-interface for http";
              }
              leaf cmpv2 {
                type empty;
                must "count(/if:interfaces/if:interface/ifxroute"
                + "r6000:l3-interface[ifxrouter6000:context=current"
                + "()/../../../../ifxrouter6000:context]/ifxrouter6"
                + "000:ip/ifxrouter6000:source-address/ifxrouter600"
                + "0:options/ifxrouter6000:cmpv2)<2" {
                  error-message "Conflict exists,cmpv2 has "
                  + "already been set under different interface "
                  + "associated with the same context.";
                  description
                    "Conflict exists,cmpv2 has already been set
                     under different interface associated with
                     the same context. ";
                }
                description
                  "Configure source-interface for cmpv2";
              }
            }
          }
          case all {
            leaf all {
              type empty;
              must "count(/if:interfaces/if:interface/ifxrouter6"
              + "000:l3-interface[ifxrouter6000:context=current()/."
              + "./../../ifxrouter6000:context]/ifxrouter6000:ip/if"
              + "xrouter6000:source-address/ifxrouter6000:all)+count"
              + "(/if:interfaces/if:interface/ifxrouter6000:l3-int"
              + "erface[ifxrouter6000:context=current()/../../../if"
              + "xrouter6000:context]/ifxrouter6000:ip/ifxrouter600"
              + "0:source-address/ifxrouter6000:options/.)<2" {
                error-message "Conflict exists, there is a "
                + "service already set for the same context.";
                description
                  "Conflict exists, there is a service already
                   set for the same context.";
              }
              description
                "Configure source-interface for all
                 applications";
            }
          }
        }
      }
      list access-group {
        key "direction";
        description
          "Apply packet access control";
        leaf direction {
          type typesrouter6000:access_group_dir;
          description
            "The direction ACL list to appiled in the interface";
        }
        leaf cls-name {
          type string {
            pattern '(\S+)|(\S+(\s\S+)*)';
          }
          mandatory true;
          description
            "access list name (up to 10 names); more than one
             ACL enter with \"\" and space separator";
        }
        leaf count {
          type empty;
          description
            "Configure access list packet counting";
        }
        leaf log {
          when "(../direction='in')" {
            description
              "The direction of acl logging can only configured
               in the inbound";
          }
          type empty;
          description
            "Configure access list packet logging";
        }
      }
      container verify-unicast-source-reachable-via {
        description
          "Specify the validation for the source address";
        choice verify-unicast-source-reachable-via-choice {
          case any {
            container any {
              presence "";
              description
                "Source IP address can be reached by any
                 interface";
              leaf rpf-count {
                type empty;
                description
                  "Enables counting of the dropped packet due to
                   RPF check fail";
              }
              leaf allow-default {
                type empty;
                description
                  "Allow RPF to lookup the default route for
                   verification";
              }
              container access-group {
                presence "";
                description
                  "Apply access control to RPF IP source address
                   selection";
                leaf access-list {
                  type string;
                  mandatory true;
                  description
                    "IP access list name(s) (up to 10 enclosed
                     in quotes)";
                }
                leaf acl-count {
                  type empty;
                  description
                    "Enable IP access list match counting";
                }
              }
            }
          }
          case receive {
            container receive {
              presence "";
              description
                "Source address must be reachable through the
                 incoming interface";
              leaf allow-default {
                type empty;
                description
                  "Allow RPF to lookup the default route for
                   verification";
              }
              container access-group {
                presence "";
                description
                  "Apply access control to RPF IP source address
                   selection";
                leaf access-list {
                  type string;
                  mandatory true;
                  description
                    "IP access list name(s) (up to 10 enclosed
                     in quotes)";
                }
                leaf acl-count {
                  type empty;
                  description
                    "Enable IP access list match counting";
                }
              }
            }
          }
        }
      }
      list tcp-mss-replace {
        key "direction";
        description
          "Enables MSS option value replacement";
        leaf direction {
          type typesrouter6000:access_group_dir;
          description
            "The direction tcp mss replace list to appiled in
             the interface";
        }
        leaf mss-size {
          type uint16 {
            range "216..16344";
          }
          mandatory true;
          description
            "Maximum Segment Size to be used when replacing the
             MSS value";
        }
      }
      leaf icmp-suppress-packet-too-big {
        type empty;
        description
          "Suppress error when a packet with DF flag is greater
           than MTU";
      }
      container pool {
        when "(../../../if:type != 'ifxrouter6000:p2pOverLan') "
        + "and (../../../if:type != "
        + "'ifxrouter6000:applicationLoopback')" {
          description
            "";
        }
        if-feature pool;
        description
          "Add an IP pool";
        choice pool-choice {
          case pool-addr {
            leaf pool-addr {
              type typesrouter6000:ipos-ip-prefix;
              description
                "IP pool address prefix";
            }
          }
          case start-addr {
            container start-addr {
              presence "";
              description
                "IP pool start IP address";
              leaf to {
                type empty;
                mandatory true;
                description
                  "Configure an IP pool range";
              }
              leaf end-addr {
                type inet:ipv4-address;
                mandatory true;
                description
                  "IP pool end IP address";
              }
            }
          }
        }
        leaf name {
          type string;
          description
            "Configure an IP pool name";
        }
        container pool-opt1 {
          presence "";
          description
            "container pool-opt1.";
          leaf falling-threshold {
            type empty;
            mandatory true;
            description
              "Configure an IP pool falling threshold";
          }
          leaf falling-threshold-size {
            type uint16 {
              range "0..65535";
            }
            mandatory true;
            description
              "falling threshold size";
          }
          choice pool-opt1-choice {
            case trap {
              container trap {
                presence "";
                description
                  "Generate SNMP trap";
                leaf log {
                  type empty;
                  description
                    "Generate log message";
                }
              }
            }
            case log {
              container log {
                presence "";
                description
                  "Generate log message";
                leaf trap {
                  type empty;
                  description
                    "Generate SNMP trap";
                }
              }
            }
          }
        }
      }
    }
    /*
    icr { link-protection | transport | prefix-advertisement [
     tracking ] }
    */
    container icr {
      when "(../../if:type != 'ifxrouter6000:p2pOverLan') and "
      + "(../../if:type != 'ifxrouter6000:applicationLoopback')" {
        description
          "";
      }
      if-feature icr;
      description
        "ICR (Inter-Chassis Resilience) configuration";
      choice icr {
        case link-protection {
          leaf link-protection {
            type empty;
            description
              "Configure multi-chassis-link-protection";
          }
        }
        case transport {
          leaf transport {
            type empty;
            description
              "Configure icr transport for MC-LAG";
          }
        }
        case prefix-advertisement {
          container prefix-advertisement {
            presence "";
            description
              "Monitor the prefix route advertised";
            leaf tracking {
              type empty;
              description
                "Enable ICR tracking";
            }
          }
        }
      }
    }
    /*
    traffic-index accounting
    */
    leaf traffic-index-accounting {
      if-feature trafic-index-accounting;
      type empty;
      description
        "Enable traffic-index accounting";
    }
    /*
    forward policy (fwd-name) in
    */
    container forward-policy {
      when "../../if:type = 'ifxrouter6000:applicationLoopback'" {
        description
          "";
      }
      presence "";
      description
        "Configure forward policy";
      leaf fwd-name {
        type string;
        mandatory true;
        description
          "Forward policy name";
      }
      leaf in {
        type empty;
        mandatory true;
        description
          "Configure inbound forward policy";
      }
    }
    /*
    counters dual-stack
    */
    leaf counters-dual-stack {
      type empty;
      description
        "dual stack for both IPv4 and IPv6";
    }
    /*
    context (ctx-name)
    */
    leaf context {
      type leafref {
        path "/ctxsr6k:contexts/ctxr6k:context/ctxr6k:context-"
        + "name";
      }
      mandatory true;
      description
        "Name of context which the interface belongs to";
    }
    /*
    p2p [strict-ipv4-validation]
    */
    container p2p {
      when "../../if:type = 'ifxrouter6000:p2pOverLan'" {
        description
          "";
      }
      description
        "P2P interface";
      leaf strict-ipv4-validation {
        type boolean;
        default "false";
        description
          "Enable/Disable strict-ipv4-validation";
      }
    }
    /*
    inter-context { p2p (ic-num) | lan (ic-num) }
    */
    container inter-context {
      when "../../if:type = 'ifxrouter6000:intercontext'" {
        description
          "";
      }
      description
        "Configure as inter-context";
      choice inter-context {
        mandatory true;
        case p2p {
          leaf p2p {
            type uint16 {
              range "1..3000";
            }
            mandatory true;
            description
              "Configure as an inter-context point-to-point";
          }
        }
        case lan {
          leaf lan {
            type uint16 {
              range "1..3000";
            }
            mandatory true;
            description
              "Configure as an inter-context LAN interface";
          }
        }
      }
    }
    /*
    evpn default-gateway
    */
    container evpn-default-gateway {
      presence "";
      description
        "Configure evpn default gateway";
      uses evpn-irb-grp;
    }
  }

  grouping evpn-irb-grp {
    description
      "Evpn irb gateway configuration mode";
    /*
    virtual-router-id (vrid)
    */
    leaf virtual-router-id {
      type uint8 {
        range "1..255";
      }
      default "1";
      description
        "Virtual Router identifier";
    }
    /*
    mac-address (mac)
    */
    leaf mac-address {
      type yang:mac-address;
      description
        "Set the MAC address";
    }
    /*
    ip address (addr)
    */
    container ip {
      description
        "IP configuration command";
      leaf address {
        type typesrouter6000:ipos-ip-prefix;
        description
          "IP address to be configured";
      }
    }
    /*
    ipv6 address (addr)
    */
    container ipv6 {
      description
        "IPv6 configuration command";
      leaf address {
        type typesrouter6000:ipv6-address-mask;
        description
          "IP address to be configured";
      }
    }
    /*
    refresh-interval (interval-val)
    */
    leaf refresh-interval {
      type uint16 {
        range "5..65535";
      }
      description
        "Configure the periodic garp/ns refresh-interval";
    }
  }

  augment "/if:interfaces/if:interface" {
    description
      "ericsson-interface";
    /*
    l3-interface
    */
    container l3-interface {
      when "../if:type = 'ianaift:ipForward' or ../if:type = "
      + "'ianaift:softwareLoopback' or ../if:type = "
      + "'ifxrouter6000:p2pOverLan' or ../if:type = "
      + "'ifxrouter6000:applicationLoopback' or ../if:type = "
      + "'ifxrouter6000:intercontext'" {
        description
          "";
      }
      presence "";
      description
        "Configure a logical interface";
      uses if-grp;
    }
  }

  augment "/if:interfaces-state/if:interface"{
       description
       "ericsson-interface-state";

       leaf config-status {
         type interface_config_type;
         config false;
         notife:notifiable-state-data true;
         description
           "interface config status";
       }
}

}
