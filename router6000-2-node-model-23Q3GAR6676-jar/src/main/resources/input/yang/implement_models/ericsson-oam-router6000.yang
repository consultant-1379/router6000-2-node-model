module ericsson-oam-router6000 {
  yang-version "1";

  namespace "urn:rdns:com:ericsson:oammodel:ericsson-oam-router6000";

  prefix "oamrouter6000";

  import ietf-inet-types {
    prefix "inet";
  }

  import ietf-interfaces {
    prefix "if";
  }

  import ericsson-types-router6000 {
    prefix "typesrouter6000";
  }

  import ericsson-contexts-router6000 {
    prefix "ctxsr6k";
  }

  import ericsson-lag-ext-router6000 {
    prefix "lagxrouter6000";
  }

  import ericsson-ethernet-ext-router6000 {
    prefix "ethxrouter6000";
  }

  import ericsson-l2-service-router6000 {
    prefix "l2servicer6k";
  }

  import ericsson-yang-extensions {
    prefix "yexte";
  }

  organization
    "Ericsson AB";

  contact
    "Web:   <http://www.ericsson.com>";

  description
    "ericsson-oam-router6000
     Copyright (c) 2021 Ericsson AB.
     All rights reserved";

  revision "2021-12-21" {
    description
      "Modify oam root command string";
    reference
      "rfc6020";
    yexte:version "3";
    yexte:release "0";
    yexte:correction "5";
  }

  revision "2021-11-26" {
    description
      "port-id-opt mandatory attribute removed";
    reference
      "rfc6020";
    yexte:version "3";
    yexte:release "0";
    yexte:correction "4";
  }

  revision "2021-11-25" {
    description
      "Change type for si-id";
    reference
      "rfc6020";
    yexte:version "3";
    yexte:release "0";
    yexte:correction "3";
  }

  revision "2021-06-02" {
    description
      "Remove mip-cct mandatory attribute";
    reference
      "rfc6020";
    yexte:version "3";
    yexte:release "0";
    yexte:correction "2";
  }

  revision "2021-05-21" {
    description
      "Fix for maintenance association as part of TR HZ19616";
    reference
      "rfc6020";
    yexte:version "3";
    yexte:release "0";
    yexte:correction "1";
  }

  revision "2020-07-03" {
    description
      "Removing y1731 and bnm if features";
    reference
      "rfc6020";
    yexte:version "3";
    yexte:release "0";
    yexte:correction "0";
  }

  revision "2020-01-10" {
    description
      "Modify port and interface tlvs to boolean types";
    reference
      "rfc6020";
    yexte:version "2";
    yexte:release "0";
    yexte:correction "2";
  }

  revision "2019-12-23" {
    description
      "Modify loopback and linktrace to boolean types";
    reference
      "rfc6020";
    yexte:version "2";
    yexte:release "0";
    yexte:correction "1";
  }

  revision "2018-11-27" {
    description
      "remove ipos choice description";
    reference
      "rfc6020";
    yexte:version "2";
    yexte:release "0";
    yexte:correction "0";
  }

  revision "2018-05-15" {
    description
      "initial revision";
    reference
      "rfc6020";
    yexte:version "1";
    yexte:release "0";
    yexte:correction "0";
  }

  grouping ether-cfm-ma-ccm-grp {
    description
      "Ethernet CFM CCM configuration mode";
    /*
    std-interval (interval-val)
    */
    leaf std-interval {
      type string {
        pattern '(3ms|10ms|100ms|1s|10s|1m)' {
          error-message "Interval value can only be 3ms | 10ms | "
          + "100ms | 1s | 10s | 1m";
        }
      }
      description
        "Configure 802.1ag Standard CCM Interval";
    }
    /*
    frame-loss (loss-val)
    */
    leaf frame-loss {
      type uint8 {
        range "3..100";
      }
      description
        "Configure CCM frame loss count";
    }
    /*
    port-status-tlv
    */
    leaf port-status-tlv {
      type empty;
      status obsolete;
      description
        "Enable/Disable Port status tlv";
    }
    /*
    interface-status-tlv
    */
    leaf interface-status-tlv {
      type empty;
      status obsolete;
      description
        "Enable/Disable Interface status tlv";
    }
    /*
    port-status-tlv-n
    */
    leaf port-status-tlv-n {
      type boolean;
      default "true";
      description
        "Enable/Disable port-status-tlv-n";
    }
    /*
    interface-status-tlv-n
    */
    leaf interface-status-tlv-n {
      type boolean;
      default "true";
      description
        "Enable/Disable interface-status-tlv-n";
    }
  }

  grouping ether-cfm-profile-grp {
    description
      "Ehternet CFM profile configuration mode";
    /*
    ccm
    */
    container ccm {
      presence "";
      description
        "Configure ccm";
      uses ether-cfm-ma-ccm-grp;
    }
    /*
    priority (priority-val)
    */
    leaf priority {
      type uint8 {
        range "0..7";
      }
      description
        "Configure priority";
    }
    /*
    loss-measurement
    */
    leaf loss-measurement {
      type empty;
      description
        "Configure loss-measurement";
    }
    /*
    delay-measurement
    */
    leaf delay-measurement {
      type empty;
      description
        "Enable delay-measurement";
    }
    /*
    synthetic-loss-measurement
    */
    leaf synthetic-loss-measurement {
      type empty;
      description
        "Configure synthetic-loss-measurement";
    }
    /*
    throughput-measurement
    */
    leaf throughput-measurement {
      type empty;
      description
        "Configure throughput-measurement";
    }
  }

  grouping performance-profile-grp {
    description
      "OAM Performance Measurement profile configuration mode";
    /*
    count (count-val)
    */
    leaf count {
      type uint32 {
        range "1..3162240000";
      }
      description
        "Specify number of packets to send";
    }
    /*
    data (data-val) [ size (size-val) ]
    */
    container data {
      presence "";
      description
        "Specify user data";
      leaf data-val {
        type string;
        mandatory true;
        description
          "User data up to 128 chars";
      }
      leaf size {
        type uint16 {
          range "0..1500";
        }
        description
          "User data bytes";
      }
    }
    /*
    interval (interval-val)
    */
    leaf interval {
      type uint16 {
        range "10..10000";
      }
      description
        "Interval between test packets (msec)";
    }
    /*
    timeout (timeout-val)
    */
    leaf timeout {
      type uint16 {
        range "10..10000";
      }
      description
        "Test session timeout (sec)";
    }
    /*
    priority (priority-val)
    */
    leaf priority {
      type uint8 {
        range "0..7";
      }
      description
        "Priority of test packets";
    }
    /*
    size (size-val)
    */
    leaf size {
      type uint16 {
        range "0..9600";
      }
      description
        "Data TLV size";
    }
    /*
    duration (duration-val)
    */
    leaf duration {
      type uint32 {
        range "1..31622400";
      }
      description
        "Number of seconds";
    }
    /*
    rate (rate-val) [ increment (increment-val) ]
    */
    container rate {
      presence "";
      description
        "Configure the base frame rate";
      leaf rate-val {
        type uint32 {
          range "1..4294967295";
        }
        mandatory true;
        description
          "Rate in frames per second";
      }
      leaf increment {
        type uint32 {
          range "0..33554432";
        }
        description
          "Increment rate";
      }
    }
    /*
    iterate (iteration-val)
    */
    leaf iterate {
      type uint8 {
        range "1..128";
      }
      description
        "Number of iterations";
    }
    /*
    drop-eligible
    */
    leaf drop-eligible {
      type empty;
      description
        "Set the drop-eligiblity bit";
    }
  }

  grouping ether-cfm-ma-grp {
    description
      "Ehternet CFM MA configuration mode";
    /*
    profile (prof-name)
    */
    leaf profile {
      type string;
      description
        "Configure profile for maintenance association";
    }
    /*
    mep (mepid) { (slot-port-id) | lg { (name) | (id) } }
     [service-instance (si-id) [ (vlan-range-value) ] | service-
     instance-conf (si-id) [ (vlan-range-value) ] | vlan-id
     (vlan-id-value) ] { direction [ up | <down [ per-
     constituent]> ] }
    */
    list mep {
      key "mepid";
      description
        "Configure the mep ID and circuit";
      leaf mepid {
        type uint16 {
          range "1..8191";
        }
        description
          "MEP ID";
      }
      choice mep-interface {
        mandatory true;
        description
          "mep interface";
        case slot-port-id {
          leaf slot-port-id {
            type leafref {
              path "/if:interfaces/if:interface/if:name";
            }
            description
              "Specify MEP circuit, format is slot/port";
          }
        }
        case lg {
          leaf lg {
            type union {
              type string {
                length "1..40";
              }
              type uint8 {
                range "1..40";
              }
            }
            description
              "Link group can be either name or id";
          }
        }
      }
      choice mep-cct {
        description
          "mep cct range";
        case service-instance {
          container service-instance {
            presence "";
            status obsolete;
            description
              "Service-instance identifier";
            leaf si-id {
              type leafref {
                path "/if:interfaces/if:interface"
                + "/ethxrouter6000:ethernet/l2servicer6k:service-instance"
                + "/l2servicer6k:spec-instance-id";
              }
              mandatory true;
              description
                "Configure SI ID";
            }
            leaf-list vlan-range-value {
              type string {
                pattern '(\*|(([1-9]|[1-9][0-9]|[1-9][0-9][0-9]|'
                + '[1-3][0-9][0-9][0-9]|40[0-8][0-9]|409[0-4])(\-(['
                + '1-9]|[1-9][0-9]|[1-9][0-9][0-9]|[1-3][0-9][0-9]['
                + '0-9]|40[0-8][0-9]|409[0-4]))?))(:(\*|([1-9]|[1-9'
                + '][0-9]|[1-9][0-9][0-9]|[1-3][0-9][0-9][0-9]|40[0'
                + '-8][0-9]|409[0-5]))(\-([1-9]|[1-9][0-9]|[1-9][0-'
                + '9][0-9]|[1-3][0-9][0-9][0-9]|40[0-8][0-9]|409[0-'
                + '4]))?)?' {
                  error-message "correct format should be "
                  + "(*|nn[-nn])[:(*|nn[-nn])]";
                }
              }
              description
                "service instance range, correct format should
                 be (*|nn[-nn])[:(*|nn[-nn])], nn is between
                 1-4095";
            }
          }
        }
        case service-instance-conf {
          container service-instance-conf {
            presence "";
            description
              "Service-instance identifier";
            leaf si-id {
              type uint32 {
                range "1..262143";
              }
              mandatory true;
              description
                "Configure SI ID";
            }
            leaf-list vlan-range-value {
              type string {
                pattern '(\*|(([1-9]|[1-9][0-9]|[1-9][0-9][0-9]|'
                + '[1-3][0-9][0-9][0-9]|40[0-8][0-9]|409[0-4])(\-(['
                + '1-9]|[1-9][0-9]|[1-9][0-9][0-9]|[1-3][0-9][0-9]['
                + '0-9]|40[0-8][0-9]|409[0-4]))?))(:(\*|([1-9]|[1-9'
                + '][0-9]|[1-9][0-9][0-9]|[1-3][0-9][0-9][0-9]|40[0'
                + '-8][0-9]|409[0-5]))(\-([1-9]|[1-9][0-9]|[1-9][0-'
                + '9][0-9]|[1-3][0-9][0-9][0-9]|40[0-8][0-9]|409[0-'
                + '4]))?)?' {
                  error-message "correct format should be "
                  + "(*|nn[-nn])[:(*|nn[-nn])]";
                }
              }
              description
                "service instance range, correct format should
                 be (*|nn[-nn])[:(*|nn[-nn])], nn is between
                 1-4095";
            }
          }
        }
        case vlan-id {
          leaf vlan-id {
            type string {
              pattern '(([1-9]|[1-9][0-9]|[1-9][0-9][0-9]|[1-3]['
              + '0-9][0-9][0-9]|40[0-8][0-9]|409[0-5])|([1-9]|[1-9]'
              + '[0-9]|[1-9][0-9][0-9]|[1-3][0-9][0-9][0-9]|40[0-8]'
              + '[0-9]|409[0-5]):?([1-9]|[1-9][0-9]|[1-9][0-9][0-9]'
              + '|[1-3][0-9][0-9][0-9]|40[0-8][0-9]|409[0-5]))' {
                error-message "correct format should be 1-4095 "
                + "or [1-4095]:[1-4095]";
              }
            }
            description
              "VLAN identifier. Correct format should be
               vlan-id[:inner-vlan-id], 1-4095 or
               [1-4095]:[1-4095]";
          }
        }
      }
      container direction {
        presence "";
        description
          "Specify mep direction";
        choice direction-opt {
          case up {
            leaf up {
              type empty;
              description
                "Specify mep direction-up";
            }
          }
          case down {
            container down {
              presence "";
              description
                "Specify mep direction-down";
              leaf per-constituent {
                type empty;
                must "/ctxsr6k:contexts/oamrouter6000:oam"
                + "/oamrouter6000:instance/oamrouter6000:cfm"
                + "/oamrouter6000:maintenance-association"
                + "/oamrouter6000:name/oamrouter6000:mep"
                + "/oamrouter6000:lg" {
                  error-message "down per-constituent can be "
                  + "configured under link group";
                  description
                    "down per-constituent can be configured
                     under link group";
                }
                description
                  "Specify mep direction-down-per-constituent";
              }
            }
          }
        }
      }
    }
    /*
    remote-mep [(low-val)] to { (high-val) }
    */
    list remote-mep {
      key "low-val";
      description
        "Configure maintenance association's remote mepid";
      leaf low-val {
        type uint16 {
          range "1..8191";
        }
        mandatory true;
        description
          "Remote MEP ID in a MA";
      }
      leaf to {
        type empty;
        description
          "Configure remote MEPID range";
      }
      leaf high-val {
        type uint16 {
          range "1..8191";
        }
        description
          "Remote MEP ID range";
      }
    }
    /*
    ccm
    */
    container ccm {
      presence "";
      description
        "Configure ccm";
      uses ether-cfm-ma-ccm-grp;
    }
    /*
    bnm
    */
    container bnm {
      presence "";
      description
        "Configure Bandwidth Notification Message";
      uses ether-cfm-ma-bnm-grp;
    }
    /*
    priority (priority-val)
    */
    leaf priority {
      type uint8 {
        range "0..7";
      }
      description
        "Configure priority";
    }
    /*
    loss-measurement
    */
    leaf loss-measurement {
      type empty;
      description
        "Configure loss-measurement";
    }
    /*
    delay-measurement
    */
    leaf delay-measurement {
      type empty;
      description
        "Enable delay-measurement";
    }
    /*
    synthetic-loss-measurement
    */
    leaf synthetic-loss-measurement {
      type empty;
      description
        "Configure synthetic-loss-measurement";
    }
    /*
    throughput-measurement
    */
    leaf throughput-measurement {
      type empty;
      description
        "Configure throughput-measurement";
    }
  }

  grouping ether-cfm-grp {
    description
      "Ehternet CFM configuration mode";
    /*
    level (level-val)
    */
    leaf level {
      type uint8 {
        range "1..7";
      }
      description
        "Configure maintenance domain level";
    }
    /*
    domain-name (domain-name)
    */
    leaf domain-name {
      type string;
      description
        "Configure maintenance domain name";
    }
    /*
    linktrace
    */
    leaf linktrace {
      type empty;
      status obsolete;
      description
        "Linktrace message responding";
    }
    /*
    loopback
    */
    leaf loopback {
      type empty;
      status obsolete;
      description
        "Loopback message responding";
    }
    /*
    link-trace
    */
    leaf link-trace {
      type boolean;
      default "true";
      description
        "Enable/Disable link-trace";
    }
    /*
    loop-back
    */
    leaf loop-back {
      type boolean;
      default "true";
      description
        "Enable/Disable loop-back";
    }
    /*
    mip (mipid) { (slot-port-id) | lg { (name) | (id) } }
     [service-instance (si-id) [ (vlan-range-value) ] | service-
     instance-new (si-id) [ (vlan-range-value) ] | vlan-id (vlan-
     id-value) ]
    */
    list mip {
      key "mipid";
      description
        "Configure the mip ID and circuit";
      leaf mipid {
        type uint16 {
          range "1..8191";
        }
        description
          "MIP ID";
      }
      choice mip-interface {
        mandatory true;
        description
          "mip interface";
        case slot-port-id {
          leaf slot-port-id {
            type leafref {
              path "/if:interfaces/if:interface/if:name";
            }
            description
              "Specify MIP circuit, format is slot/port";
          }
        }
        case lg {
          leaf lg {
            type union {
              type string {
                length "1..40";
              }
              type uint8 {
                range "1..40";
              }
            }
            description
              "Link group can be either name or id";
          }
        }
      }
      choice mip-cct {
        description
          "mip cct range";
        case service-instance {
          container service-instance {
            presence "";
            status obsolete;
            description
              "Service-instance identifier";
            leaf si-id {
              type leafref {
                path "/if:interfaces/if:interface"
                + "/ethxrouter6000:ethernet/l2servicer6k:service-instance"
                + "/l2servicer6k:spec-instance-id";
              }
              mandatory true;
              description
                "Configure SI ID";
            }
            leaf-list vlan-range-value {
              type string {
                pattern '(\*|(([1-9]|[1-9][0-9]|[1-9][0-9][0-9]|'
                + '[1-3][0-9][0-9][0-9]|40[0-8][0-9]|409[0-4])(\-(['
                + '1-9]|[1-9][0-9]|[1-9][0-9][0-9]|[1-3][0-9][0-9]['
                + '0-9]|40[0-8][0-9]|409[0-4]))?))(:(\*|([1-9]|[1-9'
                + '][0-9]|[1-9][0-9][0-9]|[1-3][0-9][0-9][0-9]|40[0'
                + '-8][0-9]|409[0-5]))(\-([1-9]|[1-9][0-9]|[1-9][0-'
                + '9][0-9]|[1-3][0-9][0-9][0-9]|40[0-8][0-9]|409[0-'
                + '4]))?)?' {
                  error-message "correct format should be "
                  + "(*|nn[-nn])[:(*|nn[-nn])]";
                }
              }
              description
                "service instance range, correct format should
                 be (*|nn[-nn])[:(*|nn[-nn])], nn is between
                 1-4095";
            }
          }
        }
        case service-instance-new {
          container service-instance-new {
            presence "";
            description
              "Service-instance identifier";
            leaf si-id {
              type uint32 {
                range "1..262143";
              }
              mandatory true;
              description
                "Configure SI ID";
            }
            leaf-list vlan-range-value {
              type string {
                pattern '(\*|(([1-9]|[1-9][0-9]|[1-9][0-9][0-9]|'
                + '[1-3][0-9][0-9][0-9]|40[0-8][0-9]|409[0-4])(\-(['
                + '1-9]|[1-9][0-9]|[1-9][0-9][0-9]|[1-3][0-9][0-9]['
                + '0-9]|40[0-8][0-9]|409[0-4]))?))(:(\*|([1-9]|[1-9'
                + '][0-9]|[1-9][0-9][0-9]|[1-3][0-9][0-9][0-9]|40[0'
                + '-8][0-9]|409[0-5]))(\-([1-9]|[1-9][0-9]|[1-9][0-'
                + '9][0-9]|[1-3][0-9][0-9][0-9]|40[0-8][0-9]|409[0-'
                + '4]))?)?' {
                  error-message "correct format should be "
                  + "(*|nn[-nn])[:(*|nn[-nn])]";
                }
              }
              description
                "service instance range, correct format should
                 be (*|nn[-nn])[:(*|nn[-nn])], nn is between
                 1-4095";
            }
          }
        }
        case vlan-id {
          leaf vlan-id {
            type string {
              pattern '(([1-9]|[1-9][0-9]|[1-9][0-9][0-9]|[1-3]['
              + '0-9][0-9][0-9]|40[0-8][0-9]|409[0-5])|([1-9]|[1-9]'
              + '[0-9]|[1-9][0-9][0-9]|[1-3][0-9][0-9][0-9]|40[0-8]'
              + '[0-9]|409[0-5]):?([1-9]|[1-9][0-9]|[1-9][0-9][0-9]'
              + '|[1-3][0-9][0-9][0-9]|40[0-8][0-9]|409[0-5]))' {
                error-message "correct format should be 1-4095 "
                + "or [1-4095]:[1-4095]";
              }
            }
            description
              "VLAN identifier. Correct format should be
               vlan-id[:inner-vlan-id], 1-4095 or
               [1-4095]:[1-4095]";
          }
        }
      }
    }
    /*
    maintenance-association [ icc (icc-val) | name (name-val) ]
    */
    container maintenance-association {
      description
        "Configure MA short name";
      list icc {
        key "icc";
        description
          "Configure ICC-based MEG ID";
        leaf icc {
          type string;
          description
            "ICC-based MEG ID";
        }
        uses ether-cfm-ma-grp;
      }
      list name {
        key "name";
        description
          "Configure MA name";
        leaf name {
          type string;
          description
            "MA short name";
        }
        uses ether-cfm-ma-grp;
      }
    }
  }

  grouping ether-cfm-ma-bnm-grp {
    description
      "Ethernet CFM BNM configuration mode";
    /*
    port-id (id-val) [ aggregate | root ]
    */
    list port-id {
      key "id-val";
      description
        "Configure BNM Port ID";
      leaf id-val {
        type uint32 {
          range "0..4294967295";
        }
        description
          "Port Number";
      }
      choice port-id-opt {
        description
          "BNM choice";
        case aggregate {
          leaf aggregate {
            type empty;
            description
              "Apply bnm aggregately for the LMEP circuit and
               all child circuits";
          }
        }
        case root {
          leaf root {
            type empty;
            description
              "Apply bnm aggregately for all circuits under the
               LMEP port";
          }
        }
      }
    }
  }

  augment "/ctxsr6k:contexts" {
    description
      "ericsson-oam";
    /*
    oam { <profile (profile-name) [ cfm | performance ]> |
     <instance (instance-id) [ cfm ] >}
    */
    container oam {
      status obsolete;
      description
        "OAM Config";
      list profile {
        key "profile-name";
        status obsolete;
        description
          "OAM Profile Config";
        leaf profile-name {
          type string;
          description
            "OAM profile name";
        }
        choice profile-opt {
          description
            "OAM CFM Profile choice";
          case cfm {
            container cfm {
              presence "";
              status obsolete;
              description
                "802.1ag CFM Config";
              uses ether-cfm-profile-grp;
            }
          }
          case performance {
            container performance {
              presence "";
              status obsolete;
              description
                "EtherOAM PM profile";
              uses performance-profile-grp;
            }
          }
        }
      }
      list instance {
        key "instance-id";
        status obsolete;
        description
          "OAM Instance Config";
        leaf instance-id {
          type uint32;
          status obsolete;
          description
            "OAM instance ID";
        }
        container cfm {
          presence "";
          status obsolete;
          description
            "802.1ag CFM Config";
          uses ether-cfm-grp;
        }
      }
    }
    /*
    oamnew { <profilen (profile-name-n) [ cfmn ] [performancen]>
     | <instancen (instance-id-n) [ cfmn ] >}
    */
    container oamnew {
      description
        "OAM Config";
      list profilen {
        key "profile-name-n";
        description
          "OAM Profile Config";
        leaf profile-name-n {
          type string;
          description
            "OAM profile name";
        }
        container cfmn {
          presence "";
          description
            "802.1ag CFM Config";
          uses ether-cfm-profile-grp;
        }
        container performancen {
          presence "";
          description
            "EtherOAM PM profile";
          uses performance-profile-grp;
        }
      }
      list instancen {
        key "instance-id-n";
        description
          "OAM Instance Config";
        leaf instance-id-n {
          type uint32;
          description
            "OAM instance ID";
        }
        container cfmn {
          presence "";
          description
            "802.1ag CFM Config";
          uses ether-cfm-grp;
        }
      }
    }
  }

}
