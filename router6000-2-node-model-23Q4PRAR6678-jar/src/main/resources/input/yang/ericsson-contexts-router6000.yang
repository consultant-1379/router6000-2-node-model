module ericsson-contexts-router6000 {
  yang-version "1";

  namespace "urn:rdns:com:ericsson:oammodel:ericsson-contexts-router6000";

  prefix "ctxsr6k";

  import ietf-yang-types {
    prefix "yang";
  }

  import ericsson-notifications {
    prefix "notife";
  }

  import ericsson-yang-extensions {
    prefix "yexte";
  }

  organization
    "Ericsson AB";

  contact
    "Web:   <http://www.ericsson.com>";

  description
    "ericsson-contexts-router6000
     Copyright (c) 2022 Ericsson AB.
     All rights reserved";

  revision "2022-04-13" {
    description
      "Add GC_FLAG_GLOBALCONFIG flag for load-balance";
    reference
      "rfc6020";
    yexte:version "3";
    yexte:release "1";
    yexte:correction "5";
  }

  revision "2022-02-18" {
    description
      "Modify support for flow-label";
    reference
      "rfc6020";
    yexte:version "3";
    yexte:release "1";
    yexte:correction "4";
  }

  revision "2022-01-06" {
    description
      "Add support for flow-label";
    reference
      "rfc6020";
    yexte:version "3";
    yexte:release "1";
    yexte:correction "3";
  }

  revision "2021-10-12" {
    description
      "remove duplicate container system";
    reference
      "rfc6020";
    yexte:version "3";
    yexte:release "1";
    yexte:correction "2";
  }

  revision "2021-02-02" {
    description
      "set container system to be obsolete";
    reference
      "rfc6020";
    yexte:version "3";
    yexte:release "1";
    yexte:correction "1";
  }

  revision "2020-06-12" {
    description
      "add service load-balance layer3/layer4";
    reference
      "rfc6020";
    yexte:version "3";
    yexte:release "1";
    yexte:correction "0";
  }

  revision "2018-11-27" {
    description
      "remove ipos choice description";
    reference
      "rfc6020";
    yexte:version "3";
    yexte:release "0";
    yexte:correction "1";
  }

  revision "2018-08-27" {
    description
      "Adding extension statement notifiable-state-data";
    reference
      "rfc6020";
    yexte:version "3";
    yexte:release "0";
    yexte:correction "0";
  }

  revision "2018-06-05" {
    description
      "Change model namespace";
    reference
      "rfc6020";
    yexte:version "2";
    yexte:release "0";
    yexte:correction "0";
  }

  revision "2018-01-16" {
    description
      "Add router node in configuration mode.";
    reference
      "rfc6020";
    yexte:version "1";
    yexte:release "2";
    yexte:correction "1";
  }

  revision "2017-12-07" {
    description
      "VRE 2366 Adding redistribute seg and service
       fabric-hello-interval yang commands";
    reference
      "rfc6020";
    yexte:version "1";
    yexte:release "2";
    yexte:correction "0";
  }

  revision "2017-11-13" {
    description
      "Add system confirmation node.";
    reference
      "rfc6020";
    yexte:version "1";
    yexte:release "1";
    yexte:correction "1";
  }

  revision "2017-10-24" {
    description
      "Leaf ifindex-persistence added for ifindex persistence
       control.";
    reference
      "rfc6020";
    yexte:version "1";
    yexte:release "1";
    yexte:correction "0";
  }

  revision "2017-09-29" {
    description
      "update revision for align the revision with released
       version";
    reference
      "rfc6020";
    yexte:version "1";
    yexte:release "0";
    yexte:correction "1";
  }

  revision "2017-07-15" {
    description
      "rate-limit-circuit-nd There is some issues when deleting
       rate-limit-circuit-nd in conf cli";
    reference
      "rfc6020";
    yexte:version "1";
    yexte:release "0";
    yexte:correction "0";
  }

  revision "2017-06-02" {
    description
      "New commands for Dot1q";
    reference
      "rfc6020";
  }

  revision "2017-03-15" {
    description
      "add subcommand for service";
    reference
      "rfc6020";
  }

  revision "2016-12-08" {
    description
      "Remove presence of command system";
    reference
      "rfc6020";
  }

  revision "2016-07-08" {
    description
      "Add a feature name for l2 access list";
    reference
      "rfc6020";
  }

  revision "2016-03-29" {
    description
      "For CLI2Yang models data node sequence change.";
    reference
      "rfc6020";
  }

  revision "2015-12-07" {
    description
      "initial revision";
    reference
      "rfc6020";
  }

  container contexts {
    description
      "Transport configuration";
    /*
    l2
    */
    container l2 {
      description
        "Layer-2 configuration under contexts";
    }
    /*
    rate-limit circuit nd (cnt-num) {interval (interval-num)}
     {drop-interval (drop-interval-num)}
    */
    container rate-limit-circuit-nd {
      presence "";
      description
        "Configure rate-limit for nd";
      leaf cnt-num {
        type uint8 {
          range "1..255";
        }
        mandatory true;
        description
          "Max no of packets";
      }
      leaf interval {
        type uint8 {
          range "1..127";
        }
        mandatory true;
        description
          "Set interval for the max packets allowed";
      }
      leaf drop-interval {
        type uint8 {
          range "1..127";
        }
        mandatory true;
        description
          "Set drop-interval";
      }
    }
    /*
    service < {multiple-contexts | inter-context routing} >
    */
    container service {
      description
        "Service commands";
      leaf multiple-contexts {
        type boolean;
        default "false";
        description
          "Enable/Disable multiple-contexts";
      }
      leaf inter-context-routing {
        type empty;
        description
          "inter-context static routing between non-local
           contexts";
      }
      container load-balance-new {
        description
          "Config load-balancing hash key";
        container ip {
          description
            "Config load-balancing hash key for IP";
          choice ip {
            case layer-3 {
              leaf layer-3 {
                type empty;
                description
                  "Hash key is from layer 3 header only";
              }
            }
            case layer-4 {
              leaf layer-4 {
                type empty;
                description
                  "Hash key is from layer 3 and layer 4 headers";
              }
            }
            case source-only {
              leaf source-only {
                type empty;
                description
                  "Hash key is from source IP Header";
              }
            }
          }
        }
        container link-group {
          description
            "Config load-balancing hash key for link-group";
          choice link-group {
            case layer-3 {
              leaf layer-3 {
                type empty;
                description
                  "Hash key is from layer 3 header only";
              }
            }
            case layer-4 {
              leaf layer-4 {
                type empty;
                description
                  "Hash key is from layer 3 and layer 4 headers";
              }
            }
            case source-only {
              leaf source-only {
                type empty;
                description
                  "Hash key is from source IP Header";
              }
            }
          }
        }
        leaf mpls-payload {
          type empty;
          description
            "Config load-balancing hash key for mpls payload";
        }
        leaf prefer-local-egress {
          type empty;
          description
            "Prefer same card/pfe egress for ecmp/link-group";
        }
        container layer-3 {
          presence "";
          description
            "Hash key is from layer 3 header only";
          leaf flow-label {
            type empty;
            description
              "Hash key is from Flow Label";
          }
        }
        container layer-4 {
          presence "";
          description
            "Hash key is from layer 3 and layer 4 headers";
          leaf flow-label {
            type empty;
            description
              "Hash key is from Flow Label";
          }
        }
      }
      container load-balance {
        status obsolete;
        description
          "Config load-balancing hash key";
        container ip {
          status obsolete;
          description
            "Config load-balancing hash key for IP";
          choice ip {
            case layer-3 {
              leaf layer-3 {
                type empty;
                status obsolete;
                description
                  "Hash key is from layer 3 header only";
              }
            }
            case layer-4 {
              leaf layer-4 {
                type empty;
                status obsolete;
                description
                  "Hash key is from layer 3 and layer 4 headers";
              }
            }
            case source-only {
              leaf source-only {
                type empty;
                status obsolete;
                description
                  "Hash key is from source IP Header";
              }
            }
          }
        }
        container link-group {
          status obsolete;
          description
            "Config load-balancing hash key for link-group";
          choice link-group {
            case layer-3 {
              leaf layer-3 {
                type empty;
                status obsolete;
                description
                  "Hash key is from layer 3 header only";
              }
            }
            case layer-4 {
              leaf layer-4 {
                type empty;
                status obsolete;
                description
                  "Hash key is from layer 3 and layer 4 headers";
              }
            }
            case source-only {
              leaf source-only {
                type empty;
                status obsolete;
                description
                  "Hash key is from source IP Header";
              }
            }
          }
        }
        leaf mpls-payload {
          type empty;
          status obsolete;
          description
            "Config load-balancing hash key for mpls payload";
        }
        leaf prefer-local-egress {
          type empty;
          status obsolete;
          description
            "Prefer same card/pfe egress for ecmp/link-group";
        }
        leaf layer-3 {
          type empty;
          status obsolete;
          description
            "Hash key is from layer 3 header only";
        }
        leaf layer-4 {
          type empty;
          status obsolete;
          description
            "Hash key is from layer 3 and layer 4 headers";
        }
      }
    }
    /*
    ifindex-persistence
    */
    leaf ifindex-persistence {
      type empty;
      description
        "Enable ifindex persistence";
    }
    /*
    router
    */
    container router {
      description
        "Configure a routing protocol under contexts";
    }
  }

  container contexts-state {
    config "false";
    notife:notifiable-state-data true;
    description
      "root container of state data under contexts";
  }

}
