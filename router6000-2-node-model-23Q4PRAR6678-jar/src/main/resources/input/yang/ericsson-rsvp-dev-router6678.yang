/*
    This is written manually.
*/

module ericsson-rsvp-dev-router6678 {
  yang-version "1";

  namespace "urn:rdns:com:ericsson:oammodel:ericsson-rsvp-dev-router6678";

  prefix "rsvpdevrouter6678";

  import ericsson-rsvp-router6000{
    prefix "rsvpr6k";
  }
  import ericsson-yang-extensions {
    prefix "yexte";
  }
  
  import ericsson-contexts-router6000 {
   prefix "ctxsr6k";
  }

  import ericsson-context-router6000 {
   prefix "ctxr6k";
  }
  
  organization
    "Ericsson AB";

  contact
    "Web:   <http://www.ericsson.com>";

  description
    "ericsson-rsvp-dev-router6678
     Copyright (c) 2022 Ericsson AB.
     All rights reserved";

  revision "2022-11-15" {
    description
      "router rsvp chain not supported";
    reference
      "rfc6020";
    yexte:version "1";
    yexte:release "0";
    yexte:correction "0";
  }

   /*Router rsvp chain not supported*/
    deviation "/ctxsr6k:contexts/ctxr6k:context/ctxr6k:router/rsvpr6k:rsvp" {
      deviate not-supported;
    }
}
