module ericsson-telemetry-ext-router6000 {
  yang-version "1";

  namespace "urn:rdns:com:ericsson:oammodel:ericsson-telemetry-ext-router6000";

  prefix "telemetryext";

  import openconfig-inet-types {
    prefix oc-inet;
  }

  import openconfig-extensions {
    prefix oc-ext;
  }

  import openconfig-telemetry-types {
    prefix oc-telemetry-types;
  }

  import openconfig-telemetry {
    prefix oc-telemetry;
  }

  // import reference model
  import ericsson-contexts-router6000 {
    prefix ctxsr6k;
  }

  import ericsson-context-router6000 {
    prefix "ctxr6k";
  }

  import ericsson-yang-extensions {
    prefix "yexte";
  }

  organization
    "Ericsson AB";

  contact
    "Web:   <http://www.ericsson.com>";

  description
    "ericsson-telemetry-ext-router6000
     Copyright (c) 2021 Ericsson AB.
     All rights reserved";

  revision "2021-06-27" {
    description
      "add STREAM_UDP identity for protocol";
    reference
      "rfc6020";
    yexte:version "1";
    yexte:release "0";
    yexte:correction "2";
  }

  revision "2021-06-22" {
    description
      "minor changes for telemetry ext";
    reference
      "rfc6020";
    yexte:version "1";
    yexte:release "0";
    yexte:correction "1";
  }

  revision "2018-07-02" {
    description
      "initial version
       add leaf context-name to associate with the local source IP address";
    reference
      "rfc6020";
    yexte:version "1";
    yexte:release "0";
    yexte:correction "0";
  }

  identity STREAM_UDP {
    base "oc-telemetry-types:STREAM_PROTOCOL";
    description
      "This identity is used as UDP config";
  }

  augment "/oc-telemetry:telemetry-system/oc-telemetry:subscriptions/oc-telemetry:persistent/oc-telemetry:subscription/oc-telemetry:config" {
    description
      "specify the context name where the local source is";
    /*
        extend the context config for the local source
    */

    leaf context-name {
      type leafref {
        path "/ctxsr6k:contexts/ctxr6k:context/ctxr6k:context-name";
      }
      description
        "Name of context which the local source belongs to";
    }

    leaf source-port {
      type uint16;
      description
        "Protocol (udp or tcp) port number for the telemetry
         stream source";
    }
  }
}
