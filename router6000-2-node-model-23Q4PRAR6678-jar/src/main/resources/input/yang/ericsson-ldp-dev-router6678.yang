/*
    This is written manually.
*/

module ericsson-ldp-dev-router6678 {
  yang-version "1";

  namespace "urn:rdns:com:ericsson:oammodel:ericsson-ldp-dev-router6678";

  prefix "ldpdevrouter6678";

  import ericsson-ldp-router6000{
    prefix "ldprouter6000";
  }
  import ericsson-yang-extensions {
    prefix "yexte";
  }
  import ericsson-contexts-router6000 {
   prefix "ctxsr6k";
  }
  import ericsson-context-router6000 {
   prefix "ctxr6k";
  }

  organization
    "Ericsson AB";

  contact
    "Web:   <http://www.ericsson.com>";

  description
    "ericsson-ldp-dev-router6678
     Copyright (c) 2022 Ericsson AB.
     All rights reserved";

  revision "2023-06-15" {
    description
      "Deviate max LDP sessions";
    reference
      "rfc6020";
    yexte:version "1";
    yexte:release "1";
    yexte:correction "1";
  }

  revision "2023-05-12" {
    description
      "router ldp chain is re-enabled and mldp is deviated";
    reference
      "rfc6020";
    yexte:version "1";
    yexte:release "1";
    yexte:correction "0";
  }

  revision "2022-11-15" {
    description
      "router ldp chain not supported";
    reference
      "rfc6020";
    yexte:version "1";
    yexte:release "0";
    yexte:correction "0";
  }
    /* Deviate max sessions */
  deviation "/ctxsr6k:contexts/ctxr6k:context/ctxr6k:router/ldprouter6000:ldp/ldprouter6000:max-session" {
     deviate replace {
         type uint16 {
            range "1..2000";
         }
         default "2000";
     }
  }
    /* Deviate mldp */
  deviation "/ctxsr6k:contexts/ctxr6k:context/ctxr6k:router/ldprouter6000:ldp/ldprouter6000:mldp" {
     deviate not-supported;
  }

}
