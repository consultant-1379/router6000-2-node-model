module ericsson-license-monitor-dev-router6678 {
  yang-version "1";

  namespace "urn:rdns:com:ericsson:oammodel:ericsson-license-monitor-dev-router6678";

  prefix "licensemonitordevrouter6678";

  import ericsson-contexts-router6000 {
    prefix "ctxsr6k";
  }

  import ericsson-license-monitor-router6000 {
    prefix "licensermonitor6k";
  }

  import ericsson-yang-extensions {
    prefix "yexte";
  }

  organization
    "Ericsson AB";

  contact
    "Web:   <http://www.ericsson.com>";

  description
    "ericsson-license-monitor-dev-router6678
     Copyright (c) 2020 Ericsson AB.
     All rights reserved";

  revision "2022-11-07" {
    description
      "deviation for ericsson-license-monitor yang file";
    reference
      "rfc6020";
      yexte:version "1";
      yexte:release "0";
      yexte:correction "0";
  }

  deviation "/ctxsr6k:contexts/licensermonitor6k:license-monitoring/licensermonitor6k:license-monitoring/licensermonitor6k:manual-unlock/"
            + "licensermonitor6k:manual-unlock/licensermonitor6k:modify/licensermonitor6k:FAT1023250_1"  {
         deviate replace {
         type uint64 {
            range "0";
          }
         }
       }

  deviation "/ctxsr6k:contexts/licensermonitor6k:license-monitoring/licensermonitor6k:license-monitoring/licensermonitor6k:manual-unlock/"
            + "licensermonitor6k:manual-unlock/licensermonitor6k:modify/licensermonitor6k:FAT1023458_1" {
         deviate replace {
         type uint64 {
            range "0..184";
          }
         }
       }

  deviation "/ctxsr6k:contexts/licensermonitor6k:license-monitoring/licensermonitor6k:license-monitoring/licensermonitor6k:manual-unlock/"
            + "licensermonitor6k:manual-unlock/licensermonitor6k:modify/licensermonitor6k:FAT1024053_25" {
         deviate replace {
         type uint64 {
            range "0";
          }
         }
       }

  deviation "/ctxsr6k:contexts/licensermonitor6k:license-monitoring/licensermonitor6k:license-monitoring/licensermonitor6k:manual-unlock/"
            + "licensermonitor6k:manual-unlock/licensermonitor6k:modify/licensermonitor6k:FAT1023483_100" {
         deviate replace {
         type uint64 {
            range "0..46";
          }
         }
       }

  deviation "/ctxsr6k:contexts/licensermonitor6k:license-monitoring/licensermonitor6k:license-monitoring/licensermonitor6k:manual-unlock/"
            + "licensermonitor6k:manual-unlock/licensermonitor6k:modify/licensermonitor6k:FAT1023953_1" {
         deviate replace {
         type uint64 {
            range "0";
          }
         }
       }

  deviation "/ctxsr6k:contexts/licensermonitor6k:license-monitoring/licensermonitor6k:license-monitoring/licensermonitor6k:manual-unlock/"
            + "licensermonitor6k:manual-unlock/licensermonitor6k:modify/licensermonitor6k:FAT1023955_1" {
         deviate replace {
         type uint64 {
            range "0";
          }
         }
       }

  deviation "/ctxsr6k:contexts/licensermonitor6k:license-monitoring/licensermonitor6k:license-monitoring/licensermonitor6k:manual-unlock/"
            + "licensermonitor6k:manual-unlock/licensermonitor6k:modify/licensermonitor6k:FAT1024215_1" {
         deviate replace {
         type uint64 {
            range "0";
          }
         }
       }
}
