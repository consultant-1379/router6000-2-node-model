/*
    This is written manually.
*/

module ericsson-oam-dev-router6678 {
  yang-version "1";

  namespace "urn:rdns:com:ericsson:oammodel:ericsson-oam-dev-router6678";

  prefix "oamdevrouter6678";

  import ericsson-oam-router6000{
    prefix "oamrouter6000";
  }
  import ericsson-yang-extensions {
    prefix "yexte";
  }
  import ericsson-contexts-router6000 {
   prefix "ctxsr6k";
  }
  import ericsson-context-router6000 {
   prefix "ctxr6k";
  }

  organization
    "Ericsson AB";

  contact
    "Web:   <http://www.ericsson.com>";

  description
    "ericsson-oam-dev-router6678
     Copyright (c) 2022 Ericsson AB.
     All rights reserved";

  revision "2022-11-15" {
    description
      "oam cfm chain not supported";
    reference
      "rfc6020";
    yexte:version "1";
    yexte:release "0";
    yexte:correction "0";
  }

   /*OAM CFM chain not supported*/
    deviation "/ctxsr6k:contexts/oamrouter6000:oamnew" {
      deviate not-supported;
    }
}
