/*
    This is written manually.
*/
module ericsson-bfd-dev-router6678 {
  yang-version "1";

  namespace "urn:rdns:com:ericsson:oammodel:ericsson-bfd-dev-router6678";

  prefix "bfddevrouter6678";

  import ericsson-bfd-router6000 {
    prefix "bfdr6k";
  }

  import ericsson-contexts-router6000 {
    prefix "ctxsr6k";
  }

  import ericsson-context-router6000 {
    prefix "ctxr6k";
  }

  import ericsson-yang-extensions {
    prefix "yexte";
  }

  organization
    "Ericsson";

  contact
    "Web:   <http://www.ericsson.com>";

  description
    "ericsson-qos-dev-router6678
     Copyright (c) 2020 Ericsson AB.
     All rights reserved";

  revision "2021-09-15" {
    description
      "Change of default value for SBFD desired transmit interval in other SF platforms";
    reference
      "rfc6020";
    yexte:version "1";
    yexte:release "1";
    yexte:correction "0";
  }

  revision "2020-12-01" {
    description
      "deviation for ericsson-bfd-ipos.";
    reference
      "rfc6020";
    yexte:version "1";
    yexte:release "0";
    yexte:correction "0";
  }

  deviation "/ctxsr6k:contexts/ctxsr6k:router/bfdr6k:s-bfd/bfdr6k:local-discriminator" {
    deviate replace {
      type string {
        pattern "0(x|X)([1]{1})([0]{1})([01]{1}[0-7]{1})";
      }
    }
  }
  deviation "/ctxsr6k:contexts/ctxr6k:context/ctxr6k:router/bfdr6k:bfd/bfdr6k:seamless-neighbor/bfdr6k:transmit-interval" {
        deviate replace {
      default "10";
    }
  }
}
